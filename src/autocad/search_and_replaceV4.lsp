(defun ReplaceTextAndMText (/ ss idx obj entity substitutions contentString searchText replaceText i)
    ; Lista de pares (texto a buscar e texto a substituir)
    (setq substitutions '(("227896D31B6" "HD-3000KP-001")
("BF9EAC41FD3" "HD--000")
("390798BC288" "HD--000")
("24367B23587" "HD--000")
("05A1752BEED" "HD--000")
("B64604489A8" "HD--000")
("B0D944A359C" "HD--000")
("6A62A21A495" "HD--000")
("929DB107D53" "HD--000")
("D16A2D186F0" "HD--000")
("6BD0C6999A2" "HD--000")
("F2BEE4563AF" "HD--000")
("94EF5E043D2" "HD--000")
("55D14C3C492" "HD--000")
("597C7E9CED1" "HD--000")
("2689C32AB57" "HD--000")
("9B821102DF2" "HD--000")
("2AAFCCA2B54" "HD--000")
("A6CA7BE9955" "HD--000")
("9B08E8F5954" "HD--000")
("E43A58A9C22" "HD--000")
("CCF71AE9B13" "HD--000")
("B644451E1A2" "HD--000")
("9EF1D6E832E" "HD--000")
("52E3611C818" "HD--000")
("7A551C5BF4E" "HD--000")
("FBC410D4391" "HD--000")
("424D616785D" "HD--000")
("6FA96C96AD8" "HD--000")
("B84B37B5A67" "HD--000")
("B875A917E1F" "HD--000")
("E05BBE209D4" "HD--000")
("90DA4777842" "HD--000")
("F9CC23419DB" "HD--000")
("2CD4CD25B0B" "HD--000")
("B4AA3D3EF7F" "HD--000")
("EC328F7437C" "HD--000")
("C3E29812B23" "HD--000")
("2E8ABAB3571" "HD--000")
("559AB9153D8" "HD--000")
("5B459837FF8" "HD--000")
("6A3829F7F31" "HD--000")
("2D4E3436B13" "HD--000")
("E29711BD352" "HD--000")
("86667357C54" "HD--000")
("523081A9417" "HD--000")
("FC14EEBB36A" "HD--000")
("E4D5AEAA8DC" "HD--000")
("4E2436BC336" "HD--000")
("93C1BC352BA" "HD--000")
("667313C4056" "HD--000")
("3081A541741" "HD--000")
("1949AB9193D" "HD--000")
("0C30C14EEB7" "HD--000")
("3AE3C2DE743" "HD--000")
("165C3ACBE05" "HD--000")
("679CB49E5B9" "HD--000")
("A47768313C1" "HD--000")
("15675C1EA45" "HD--000")
("E79D17B73B2" "HD--000")
("6E9EAB3BEC3" "HD--000")
("5B3A76AF4A7" "HD--000")
("91F8939ADA4" "HD--000")
("ABAB3571559" "HD--000")
("DEC4862BC3B" "HD--000")
("154E3BB46A3" "HD--000")
("C6C3A36495B" "HD--000")
("6ABAE38AAD5" "HD--000")
("711BD352CAA" "HD--000")
("DEACE4CB1DE" "HD--000")
("081A9417415" "HD--000")
("B6633AD2A09" "HD--000")
("16A76498FAD" "HD--000")
("436BC336D71" "HD--000")
("834AC932223" "HD--000")
("DC2EFD5D761" "HD--000")
("17415833FF8" "HD--000")
("AE7C6D47431" "HD--000")
("A91BE10389F" "HD--000")
("03A4D2CE463" "HD--000")
("1EEE0B9B5C8" "HD--000")
("234192B6528" "HD--000")
("859C773F7E2" "HD--000")
("71623B775A9" "HD--000")
("5B35478C447" "HD--000")
("DB59F5B9603" "HD--000")
("334FDF9CC23" "HD--000")
("85C2FA56B56" "HD--000")
("D17B73B32A5" "HD--000")
("A67F7A9ED5B" "HD--000")
("7547C1747DC" "HD--000")
("8939BDA4776" "HD--000")
("C468155ABB9" "HD--000")
("163E9908AED" "HD--000")
("BF77F26E5E6" "HD--000")
("F7032729479" "HD--000")
("36B1336DB55" "HD--000")
("45BDA43334F" "HD--000")
("24911634192" "HD--000")
("ED85B859C77" "HD--000")
("77036E5E6BF" "HD--000")
("BB9ED503547" "HD--000")
("0077A2B5935" "HD--000")
("F2E87778424" "HD--000")
("AB91933C90C" "HD--000")
("59C7733BD2A" "HD--000")
("C6D3632065B" "HD--000")
("4787B1177A2" "HD--000")
("C5A46BEB534" "HD--000")
("E1B9B5D9DE0" "HD--000")
("8F82DB8EB9D" "HD--000")
("C763E7D2616" "HD--000")
("13A7649907E" "HD--000")
("CBE05BBE209" "HD--000")
("9F6BA613334" "HD--000")
("A8A487CDEC4" "HD--000")
("861BC3BC14A" "HD--000")
("A73A22A4956" "HD--000")
("B375A917ECB" "HD--000")
("E48FBE64DD8" "HD--000")
("9BDA47778F2" "HD--000")
("604489A8042" "HD--000")
("934A359837E" "HD--000")
("E79D6C6D3A3" "HD--000")
("317284787B1" "HD--000")
("1336DB56F27" "HD--000")
("52B9A9B68A0" "HD--000")
("18658D2958F" "HD-3940KP-001")
("701A1352BEE" "HD-3940KP-002")
("984A859C773" "HD-3940KP-003")
("D6D15F512A6" "HD-3940KP-004")
("DB107D5769A" "HD-3940KP-005")
("7EE253C17C3" "HD-3940KP-006")
("C936667313C" "HD-3940KP-007")
("66BCDA2750A" "HD-3940KP-008")
("A19AE28C95D" "HD-3940KP-009")
("1083845D587" "HD-3940KP-010")
("BA18FCBF49F" "HD-3940KP-011")
("46DC56068A7" "HD-3940KP-012")
("03324ACE8CC" "HD-3940KP-013")
("89A8042D78E" "HD-3940KP-014")
("68CB6A22AC1" "HD-3940KP-015")
("9F916E698D8" "HD-3940KP-016")
("3D1325AF225" "HD-3940KP-017")
("FD77249B831" "HD-3940KP-018")
("CCD9BD3AAFC" "HD-3940KP-019")
("1E6F883E52F" "HD-3940KP-020")
("4722DD69C6B" "HD-3940KP-021")
("E6BEBA8ED4F" "HD-3940KP-022")
("BDBF55BCE61" "HD-3940KP-023")
("05E1696FEED" "HD-3940KP-024")
("51E1A2D3452" "HD-3940KP-025")
("193DC9FC9D1" "HD-3940KP-026")
("BB73B26A5A6" "HD-3940KP-027")
("6DA97DC3A23" "HD-3940KP-028")
("145911475000" "HD-3940KP-029")
("49FDA477784" "HD-3940KP-030")
("BD7AAF12E7B" "HD-3940KP-031")
("83DE5DE36C1" "HD-3940KP-032")
("95D54C7C892" "HD-3940KP-033")
("9CB107D5325" "HD-3940KP-034")
("16C8B31AA5B" "HD-3940KP-035")
("130ACCCD579" "HD-3940KP-036")
("04489A8042D" "HD-3940KP-037")
("CC3BD21BF77" "HD-3940KP-038")
("9BF8E8F5C58" "HD-3940KP-039")
("A0A2C02149E" "HD-3940KP-040")
("558FD77239B" "HD-3940KP-041")
("E97778468D5" "HD-3940KP-042")
("B3AE3C2DE73" "HD-3000KP-002")
("EC218E687AB" "HD-3000KP-003")
("0EB2EB03DDA" "HD-3000KP-004")
("D558B937C39" "HD-3000KP-005")
("A7144451E19" "HD-3000KP-006")
("9DAB91933C9" "HD-3940KP-043")
("00BC47A493A" "HD--000")
("BFBB9ED5035" "HD--000")
("1499114B5E3" "HD--000")
("DE574DCCCD9" "HD--000")
("35E627896D7" "HD--000")
("B6528526944" "HD--000")
("B707AE9EAB4" "HD--000")
("0FD3290798B" "HD--000")
("9D458A927C3" "HD--000")
("5309CCBD979" "HD--000")
("C116775C2FA" "HD--000")
("55B56AD4840" "HD--000")
("4AA3D3E0803" "HD--000")
("E43A18658D2" "HD--000")
("413A923C357" "HD--000")
("4D11028AC6A" "HD--000")
("C23429DB612" "HD--000")
("4CD21B08813" "HD--000")
("4C2B3819CA0" "HD--000")
("A2C02149E11" "HD--000")
("F75EE9A1309" "HD--000")
("3334F249116" "HD--000")
("A3CB639637A" "HD--000")
("B86AD8844CE" "HD-3940KP-044")
("92728E2EDB1" "HD-3940KP-045")
("C8AC2A9EBC9" "HD--000")
("D85B859C773" "HD--000")
("D68C5B5C252" "HD--000")
("5498FADFD27" "HD--000")
("B235C705E16" "HD--000")
("DA43324ECE8" "HD--000")
("3E3453A3C86" "HD--000")
("B2EC14EEA6E" "HD--000")
("9D2C2DE6320" "HD--000")
("87D5CDC126C" "HD--000")
("2476E49F541" "HD--000")
("E1213DBD7BB" "HD--000")
("6786D20B56C" "HD--000")
("9BF39C95D44" "HD--000")
("1A1BD5D1E44" "HD--000")
("E5DA9D27D9C" "HD--000")
("DC56068A714" "HD--000")
("879135D2278" "HD--000")
("1E6B84EE5DF" "HD--000")
("65F4BB46A39" "HD--000")
("3A070327294" "HD--000")
("BDCF59BCE65" "HD--000")
("23CE574DCCB" "HD--000")
("B84EE5DF43D" "HD--000")
("6DD68C5B5C2" "HD--000")
("C476B6D8BDC" "HD--000")
("49D013A923C" "HD--000")
("39B821102CE" "HD--000")
("5A337453A3C" "HD--000")
("3570449AA80" "HD--000")
("BAD37DAD43B" "HD--000")
("1A1352BEEDF" "HD--000")
("B1B3D1325AF" "HD--000")
("F03A822CD46" "HD--000")
("E87778468D5" "HD--000")
("1634182BA52" "HD--000")
("31D250FBB47" "HD--000")
("C5B5C2521E5" "HD--000")
("F625659EE55" "HD--000")
("4B6E4DF585E" "HD--000")
("898A535E737" "HD--000")
("675C5E985B8" "HD--000")
("15833FB3AE3" "HD--000")
("8D9B3FEC218" "HD--000")
("A24367C3369" "HD--000")
("715B1752BEE" "HD--000")
("89535E32789" "HD--000")
("2AEC7239237" "HD--000")
("6C1D91881A0" "HD--000")
("7819CA0E6C4" "HD--000")
("3A041FD3294" "HD--000")
("3547CD447E8" "HD--000")
("D2CD463CBBB" "HD--000")
("8424D516785" "HD--000")
("70943F63047" "HD--000")
("DDA6D59D7C8" "HD--000")
("5DA97CB3913" "HD--000")
("D127DD142B0" "HD--000")
("24D116785C2" "HD--000")
("B6127126904" "HD--000")
("B7076E9EAB4" "HD--000")
("BED329F7547" "HD--000")
("8C3F39812B2" "HD--000")
("585E12129BD" "HD--000")
("376BCDB3750" "HD--000")
("67D67BA5922" "HD--000")
("68C5A4B2925" "HD--000")
("BE9956D14D3" "HD--000")
("C3BC24BEB7F" "HD--000")
("66E8E9B3BEC" "HD--000")
("DD4A30E37C3" "HD--000")
("AD53CC7DE2E" "HD--000")
("8AAAB357154" "HD--000")
("7896E31B67D" "HD--000")
("237615CC58B" "HD--000")
("5A4B1915383" "HD--000")
("614658D2558" "HD--000")
("FD77139B821" "HD--000")
("DA2B54EA1EB" "HD--000")
("3\"-005674C1E945B4459839EE7AD7" "3000KP-ACI-3\"-C1F-1266")
("3\"-79F2E87778468D455A7A5C6FE9" "3000KP-ACI-3\"-C1F-1267")
("1\"-5B96AD8844CF3B42B38A876BA2" "3000KP-ACI-1\"-C1F-1268")
("3\"-682A6ABCA2A4FE4A1DBB3DD95D" "3000KP-ACI-3\"-C1F-1269")
("1\"-48C7C891DCA1F64D565AAE558B" "3000KP-ACI-1\"-C1F-1270")
("3\"-94EF6E047D2EA34992B8CE6E20" "3000KP-ACI-3\"-C1F-1271")
("1\"-55B29769E4A6914E883AAC9466" "3000KP-ACI-1\"-C1F-1272")
("4\"-8739648B662D6C415F58296539" "3000KP-ACI-4\"-C1F-1273")
("1\"-BE64DD79F2E87747846AD55A78" "3000KP-ACI-1\"-C1F-1274")
("4\"-5C6FE95B96AD88444CF9B2B38C" "3000KP-ACI-4\"-C1F-1275")
("3\"-876BA2C0214990413A5B3CE574" "3000KP-ACI-3\"-C1F-0958")
("3\"-DCCBD8682A6ABC4A2A4BEA1DBF" "3000KP-ACI-3\"-C1F-0959")
("2 1/2\"-3DD95D48C7C8914DCA1B6D5659" "3000KP-ACI-2 1/2\"-C1F-0960")
("3\"-AE558BA38D49854E1219DBD7BB" "3000KP-ACI-3\"-C1F-0961")
("3\"-012F7B94EF6E0447D2EA3992B1" "3000KP-ACI-3\"-C1F-0962")
("4\"-CE6E2055B297694E4A6A1E8839" "3000KP-ACI-4\"-C1F-0963")
("3\"-8844CF3B2B38C8476BA8C02149" "3000KP-ACI-3\"-C1F-1025")
("3\"-9013A5D3CE574D4CCBDA682A6A" "3000KP-ACI-3\"-C1F-1026")
("3\"-BCA2A4FEA1DBF34DD95B48C7C8" "3000KP-ACI-3\"-C1F-1027")
("4\"-91DCA1F6D5659A4E558AA38D49" "3000KP-ACI-4\"-C1F-1028")
("3\"-8DEEC4D721C31D425FFA706AE9" "3000KP-ACI-3\"-C1F-1092")
("2 1/2\"-EAB30ED329F7984BC17AADC5A0" "3000KP-ACI-2 1/2\"-C1F-1093")
("3\"-B2B38C876BA2C042149A013A5D" "3000KP-ACI-3\"-C1F-1277")
("4\"-3CE574DCCBD86842A6AACA2A4F" "3000KP-ACI-4\"-C1F-1277")
("3\"-6D5659AE558BA348D49A5E1213" "3000KP-ACI-3\"-C1F-1278")
("3\"-DBD7BB012F7B944EF6E847D2EA" "3000KP-ACI-3\"-C1F-1279")
("3\"-1E945B459837EE47AD7A6D3B37" "3000KP-ACI-3\"-C1F-1280")
("1\"-5A5C7ACBE48BBE464DD99F2E87" "3000KP-ACI-1\"-C1F-1281")
("3\"-844CF3B2B38C8746BA2A021499" "3000KP-ACI-3\"-C1F-1283")
("4\"-013A5D3CE574DC4CBD8982A6AB" "3000KP-ACI-4\"-C1F-1283")
("1\"-CA2A4FEA1DBF3D4D95D98C7C89" "3000KP-ACI-1\"-C1F-1284")
("3\"-5E1213DBD7BB0142F7BA4EF6E0" "3000KP-ACI-3\"-C1F-1285")
("1\"-47D2EA3992B1CE46E2095B2976" "3000KP-ACI-1\"-C1F-1286")
("4\"-05674C1E945B4549837BE7AD7C" "3000KP-ACI-4\"-C1F-1287")
("1\"-6D3B375A5C7ACB4E48BAE64DD7" "3000KP-ACI-1\"-C1F-1288")
("3\"-9F2E87778468D545A789C6FE95" "3000KP-ACI-3\"-C1F-0964")
("3\"-B96AD8844CF3B24B38CA76BA2C" "3000KP-ACI-3\"-C1F-0965")
("3\"-021499013A5D3C4E574BCCBD86" "3000KP-ACI-3\"-C1F-0966")
("2 1/2\"-82A6ABCA2A4FEA41DBF9DD95D4" "3000KP-ACI-2 1/2\"-C1F-0967")
("3\"-8C7C891DCA1F6D45659AE558BA" "3000KP-ACI-3\"-C1F-0968")
("3\"-38D4985E1213DB4D7BB812F7B9" "3000KP-ACI-3\"-C1F-0969")
("4\"-4EF6E047D2EA39492B1AE6E205" "3000KP-ACI-4\"-C1F-0970")
("3\"-AC946667E13C0045674A1E945B" "3000KP-ACI-3\"-C1F-1029")
("3\"-459837EE7AD7C64D3B395A5C7A" "3000KP-ACI-3\"-C1F-1030")
("3\"-CBE48BBE64DD794F2E89778468" "3000KP-ACI-3\"-C1F-1031")
("4\"-D55A785C6FE95B496ADA844CF3" "3000KP-ACI-4\"-C1F-1032")
("3\"-7DB8255562F2BE4E4569AFD833" "3000KP-ACI-3\"-C1F-1094")
("3\"-9348B262D6DC5F4512A85498F6" "3000KP-ACI-3\"-C1F-1095")
("2 1/2\"-E6C46589D457A9427C3A74D110" "3000KP-ACI-2 1/2\"-C1F-1096")
("1\"-E558BA38D4985E41213BBD7BB0" "3940KP-ACI-1\"-C1F-009")
("1\"-12F7B94EF6E0474D2EA9992B1C" "3940KP-ACI-1\"-C1F-010")
("1\"-E6E2055B29769E44A698E8839A" "3940KP-ACI-1\"-C1F-011")
("1\"-C946667E13C0054674C8E945B4" "3940KP-ACI-1\"-C1F-012")
("6\"-59837EE7AD7C6D43B379A5C7AC" "3940KP-ACI-6\"-C1F-013")
("6\"-55A785C6FE95B946AD8A44CF3B" "3940KP-ACI-6\"-C1F-014")
("6\"-CE574DCCBD86824A6ABAA2A4FE" "3940KP-ACI-6\"-C1F-015")
("6\"-D5659AE558BA384D4989E1213D" "3940KP-ACI-6\"-C1F-016")
("6\"-992B1CE6E2055B42976AE4A691" "3940KP-ACI-6\"-C1F-017")
("6\"-5B29769E4A691E48839AC94666" "3940KP-ACI-6\"-C1F-001")
("6\"-7E13C005674C1E4945B959837E" "3940KP-ACI-6\"-C1F-002")
("6\"-E7AD7C6D3B375A45C7AABE48BB" "3940KP-ACI-6\"-C1F-003")
("6\"-E64DD79F2E877748468B55A785" "3940KP-ACI-6\"-C1F-004")
("4\"-C6FE95B96AD88444CF3A2B38C8" "3940KP-ACI-4\"-C1F-005")
("4\"-76BA2C0214990143A5D9CE574D" "3940KP-ACI-4\"-C1F-006")
("4\"-CCBD8682A6ABCA42A4FBA1DBF3" "3940KP-ACI-4\"-C1F-007")
("4\"-DD95D48C7C891D4CA1F9D5659A" "3940KP-ACI-4\"-C1F-008")
("6\"-E945B459837EE74AD7C9D3B375" "3000KP-ACI-6\"-C1F-1290")
("6\"-E8839AC946667E413C085674C1" "3000KP-ACI-6\"-C1F-1000")
("6\"-17E676ABF679CB449E5A96F232" "3000KP-ACI-6\"-C1F-1097")
("4\"-A2A4FEA1DBF3DD495D4AC7C891" "3000KP-ACI-4\"-C1F-1392")
("4\"-DCA1F6D5659AE5458BA98D4985" "3000KP-ACI-4\"-C1F-1393")
("X\"-E1213DBD7BB0124F7B99EF6E04" "3000KP-ACI-X\"-C1F-1394")
("1\"-391898CD288BEC46B17AB82444" "3000KP-ACI-1\"-C1F-1395")
("3\"-F8EE72734B475B4A18FABF590B" "3000KP-ACI-3\"-C1F-1396")
("3\"-7D2EA3992B1CE64E2059B29769" "3000KP-ACI-3\"-C1F-1397")
("X\"-1A27B765A91BE14F388BF394C2" "3000KP-ACI-X\"-C1F-1398")
("3\"-BD463CBBAC75814959BA91A3ED" "3000KP-ACI-3\"-C1F-1399")
("3\"-90CAE2CC84C37B46B788CB9FE5" "3000KP-ACI-3\"-C1F-1400")
("X\"-A5C7ACBE48BBE644DD7AF2E877" "3000KP-ACI-X\"-C1F-1401")
("3\"-78468D55A785C64FE95A96AD88" "3000KP-ACI-3\"-C1F-1402")
("3\"-44CF3B2B38C8764BA2C8214990" "3000KP-ACI-3\"-C1F-1403")
("8\"-13A5D3CE574DCC4BD86A2A6ABC" "3000KP-ACI-8\"-C1F-1404")
("3\"-E4A691E8839AC9446669E13C00" "3000KP-ACI-3\"-C1F-1405")
("3\"-96AD8844CF3B2B438C896BA2C0" "3000KP-ACI-3\"-C1F-1406")
("3\"-8D4985E1213DBD47BB082F7B94" "3000KP-ACI-3\"-C1F-1407")
("4\"-EF6E047D2EA39942B1CB6E2055" "3000KP-ACI-4\"-C1F-1408")
("4\"-B29769E4A691E84839AA946667" "3000KP-ACI-4\"-C1F-1409")
("4\"-B31AA4ACEB588849135B227886" "3000KP-ACI-4\"-C1F-1410")
("4\"-7B95E06E154E3A4A3598829E6E" "3000KP-ACI-4\"-C1F-1411")
("4\"-EC3D4F3437C13346DB59F27A71" "3000KP-ACI-4\"-C1F-1412")
("4\"-1213D027FF412F470989F63047" "3000KP-ACI-4\"-C1F-1413")
("4\"-33FF8AE7C6D47443166A7ACBE4" "3000KP-ACI-4\"-C1F-1414")
("4\"-5BCE619E8A13F948879925D626" "3000KP-ACI-4\"-C1F-1415")
("4\"-CDB3B50EB2EB034DDA6B59D7C8" "3000KP-ACI-4\"-C1F-1416")
("4\"-7EBA8DD4A243674C336A715B27" "3000KP-ACI-4\"-C1F-1417")
("4\"-C8355562F2BFE44563B8D834A3" "3000KP-ACI-4\"-C1F-1418")
("4\"-158E3EA3A92C2D4E7E2865C3A8" "3000KP-ACI-4\"-C1F-1419")
("4\"-BF590CE65DE8E043F9BABD4682" "3000KP-ACI-4\"-C1F-1420")
("4\"-FF4564B0D934A3448739EE79D6" "3000KP-ACI-4\"-C1F-1421")
("4\"-3C4919CA1B2D124159E814B933" "3000KP-ACI-4\"-C1F-1422")
("4\"-BC352BAAAB79B1488DAA80932C" "3000KP-ACI-4\"-C1F-1423")
("4\"-90DAE2CC88147046F7C8CBAFE6" "3000KP-ACI-4\"-C1F-1424")
("4\"-F3437CC336D8164F27A91EFE0B" "3000KP-ACI-4\"-C1F-1425")
("4\"-682A5ABCA2A4ED4A1DAB2CC95D" "3000KP-ACI-4\"-C1F-1426")
("4\"-9D2B1CD622F54B429BABE3AAD1" "3000KP-ACI-4\"-C1F-1427")
("4\"-1AE5A1EB588895435E287896D3" "3000KP-ACI-4\"-C1F-1428")
("4\"-D8349348B262D64DC50912A254" "3000KP-ACI-4\"-C1F-1429")
("1 1/2\"-FE6C42149D413A4923C9574D11" "3000KP-ACI-1 1/2\"-C1F-1430")
("1 1/2\"-35BD09DD23429D4B722A137615" "3000KP-ACI-1 1/2\"-C1F-1431")
("1 1/2\"-E13C005674C1E9445B499837EE" "3000KP-ACI-1 1/2\"-C1F-1432")
("3\"-6DED237DD143B146C21B79A9B6" "3000KP-ACI-3\"-C1F-1433")
("3\"-46F4489A8F42C748E78A06A73B" "3000KP-ACI-3\"-C1F-1434")
("3\"-22A4957E7A8DD44A30E87C3E29" "3000KP-ACI-3\"-C1F-1435")
("1 1/2\"-711B2352CEEE0749B58ADEFC59" "3000KP-ACI-1 1/2\"-C1F-1436")
("1 1/2\"-72CD4CD21B0770436F5B6B4BFD" "3000KP-ACI-1 1/2\"-C1F-1437")
("1 1/2\"-3D503547C1447E4C66088A71F0" "3000KP-ACI-1 1/2\"-C1F-1438")
("3\"-5674C1E945B4594837EB7AD7C6" "3000KP-ACI-3\"-C1F-1439")
("3\"-D3B375A5C7ACBE448BBB64DD79" "3000KP-ACI-3\"-C1F-1440")
("3\"-F2E87778468D554A785A6FE95B" "3000KP-ACI-3\"-C1F-1441")
("1 1/2\"-21499013A5D3CE4574DACBD868" "3000KP-ACI-1 1/2\"-C1F-1442")
("1 1/2\"-2A6ABCA2A4FEA14DBF3BD95D48" "3000KP-ACI-1 1/2\"-C1F-1443")
("1 1/2\"-C7C891DCA1F6D54659AB558BA3" "3000KP-ACI-1 1/2\"-C1F-1444")
("8\"-946667E13C0056474C1B945B45" "3000KP-ACI-8\"-C1F-1445")
("8\"-7AD7C6D3B375A54C7ACAE48BBE" "3000KP-ACI-8\"-C1F-1446")
("8\"-64DD79F2E877784468D95A785C" "3000KP-ACI-8\"-C1F-1447")
("1\"-6FE95B96AD88444CF3B8B38C87" "3000KP-ACI-1\"-C1F-1448")
("3\"-6BA2C0214990134A5D3AE574DC" "3000KP-ACI-3\"-C1F-1449")
("3\"-2F7B94EF6E047D42EA3A92B1CE" "3000KP-ACI-3\"-C1F-1450")
("4\"-6E2055B29769E44A691B8839AC" "3000KP-ACI-4\"-C1F-1451")
("4\"-55D04C3C4919CA41B2D82159E1" "3000KP-ACI-4\"-C1F-1452")
("8\"-67357C549674C54ED85A859C77" "3000KP-ACI-8\"-C1F-1453")
("3\"-EF7AD7C6D37331465C7ACBE44B" "3000KP-ACI-3\"-C1F-1454")
("3\"-BE609D89F2E877478429D51678" "3000KP-ACI-3\"-C1F-1455")
("8\"-CBD8682A6ABCA24A4FEA1DBF3D" "3000KP-ACI-8\"-C1F-1456")
("3\"-D95D48C7C891DC4A1F6B5659AE" "3000KP-ACI-3\"-C1F-1457")
("3\"-558BA38D4985E14213DAD7BB01" "3000KP-ACI-3\"-C1F-1458")
("8\"-3A5D3CE574DCCB4D8688A6ABCA" "3000KP-ACI-8\"-C1F-1459")
("3\"-1DBF3DD95D48C74C891BCA1F6D" "3000KP-ACI-3\"-C1F-1460")
("3\"-8839AC946667E143C009674C1E" "3000KP-ACI-3\"-C1F-1461")
("3\"-945B459837EE7A4D7C6B3B375A" "3000KP-ACI-3\"-C1F-1462")
("3\"-5C7ACBE48BBE644DD79B2E8777" "3000KP-ACI-3\"-C1F-1463")
("1\"-8468D55A785C6F4E95BA6AD884" "3000KP-ACI-1\"-C1F-1464")
("4\"-4CF3B2B38C876B4A2C08149901" "3000KP-ACI-4\"-C1F-1465")
("4\"-36CB45E17960EE4DFACB4CC1EE" "3000KP-ACI-4\"-C1F-1466")
("4\"-3A3CC639648B66422AC89F9169" "3000KP-ACI-4\"-C1F-1467")
("4\"-21E44A59A9C23949C4D9B68D0C" "3000KP-ACI-4\"-C1F-1468")
("4\"-A8889535E7278946E71AA7DA7B" "3000KP-ACI-4\"-C1F-1469")
("4\"-C773E7E261623B4775AA17E1F3" "3000KP-ACI-4\"-C1F-1470")
("4\"-AE568BA38D4A854E2219DBD7BB" "3000KP-ACI-4\"-C1F-1471")
("4\"-7897E31C77D68C4F6A68A11949" "3000KP-ACI-4\"-C1F-1472")
("4\"-9A2ADB217E63264BF629CB45E5" "3000KP-ACI-4\"-C1F-1473")
("4\"-9C835556DF2BFE44563A0D834A" "3000KP-ACI-4\"-C1F-1474")
("4\"-AB0E9D55D14C3C44929BB1B3D1" "3000KP-ACI-4\"-C1F-1475")
("4\"-2049D013A923CE4474DACBD8AC" "3000KP-ACI-4\"-C1F-1476")
("4\"-921634292BA5284526994118BF" "3000KP-ACI-4\"-C1F-1477")
("4\"-5A4B1511E43A584A9C2899C4D7" "3000KP-ACI-4\"-C1F-1478")
("4\"-4E0685EDDDEA8A44B7CBEB3C61" "3000KP-ACI-4\"-C1F-1479")
("4\"-A6CA7BE9951914483849D987CB" "3000KP-ACI-4\"-C1F-1480")
("4\"-7E676ABF679CB449E5AA6F2324" "3000KP-ACI-4\"-C1F-1481")
("4\"-CAC6A9E01E6A834DE5DB36C1D9" "3000KP-ACI-4\"-C1F-1482")
("4\"-6CC5F5129253984E6DAAD37D9C" "3000KP-ACI-4\"-C1F-1483")
("4\"-FD77289B8355564DF2BBE4563B" "3000KP-ACI-4\"-C1F-1484")
("4\"-1E944A459837EE47AD6A6D3B36" "3000KP-ACI-4\"-C1F-1485")
("4\"-E4E614658D24574ED67839B821" "3000KP-ACI-4\"-C1F-1486")
("4\"-CBD8AC2AAEBCA24A44DA1DBF3D" "3000KP-ACI-4\"-C1F-1487")
("4\"-EAA3592829E2ED4B2179676AFF" "3000KP-ACI-4\"-C1F-1488")
("4\"-336D715F27961E4EE0BAB5C8DE" "3000KP-ACI-4\"-C1F-1489")
("3\"-63B4D874A748B6462D6B150512" "3000KP-ACI-3\"-C1F-1490")
("4\"-3EEC218E687AB0467ACA49E5B9" "3000KP-ACI-4\"-C1F-1491")
("1\"-936667313B0F56464B1B944A45" "3000KP-ACI-1\"-C1F-1492")
("3\"-F39D95D44C7C89419CA8F6D531" "3000KP-ACI-3\"-C1F-1493")
("1\"-16B2D186F0A02441ADDBE68A47" "3000KP-ACI-1\"-C1F-1494")
("3\"-489A8F42D78E784CB7A93BD2A0" "3000KP-ACI-3\"-C1F-1495")
("3\"-4919CA1B2D12154AE119B933DF" "3000KP-ACI-3\"-C1F-1496")
("3\"-585ECCCD9BD3BA40CDB9B54EB2" "3000KP-ACI-3\"-C1F-1497")
("3\"-EB03DDAA25927148D2EBB10725" "3000KP-ACI-3\"-C1F-1498")
("3\"-769EF6691A48344AC938223ECE" "3000KP-ACI-3\"-C1F-1499")
("3\"-80B123071A54174415893EA3AD" "3000KP-ACI-3\"-C1F-1500")
("4\"-2C2DE733165C3A4CBE09ABE1F8" "3000KP-ACI-4\"-C1F-1501")
("3\"-9F6B9613334FD049DC29419DB6" "3000KP-ACI-3\"-C1F-1502")
("3\"-1281269040B4BA44D3E8804276" "3000KP-ACI-3\"-C1F-1503")
("3\"-9837EE7AD7C6D34B375A5C7ACB" "3000KP-ACI-3\"-C1F-1504")
("3\"-E48BBE64DD79F24E87798468D5" "3000KP-ACI-3\"-C1F-1505")
("3\"-5A785C6FE95B964AD8894CF3B2" "3000KP-ACI-3\"-C1F-1506")
("3\"-B38C876BA2C0214499083A5D3C" "3000KP-ACI-3\"-C1F-1507")
("3\"-E574DCCBD8682A46ABCA2A4FEA" "3000KP-ACI-3\"-C1F-1508")
("4\"-5659AE558BA38D44985B1213DB" "3000KP-ACI-4\"-C1F-1509")
("3\"-D7BB012F7B94EF46E049D2EA39" "3000KP-ACI-3\"-C1F-1510")
("3\"-92B1CE6E2055B249769B4A691E" "3000KP-ACI-3\"-C1F-1511")
("3\"-674C1E945B4598437EE9AD7C6D" "3000KP-ACI-3\"-C1F-1512")
("3\"-3B375A5C7ACBE448BBE94DD79F" "3000KP-ACI-3\"-C1F-1513")
("3\"-2E87778468D55A4785C9FE95B9" "3000KP-ACI-3\"-C1F-1514")
("4\"-DB8EB9D1BB73B246A5A97EBA8E" "3000KP-ACI-4\"-C1F-1515")
("4\"-07D5769AE669CA448E4A85E222" "3000KP-ACI-4\"-C1F-1516")
("4\"-D979376BCDA37540AB2AB039D9" "3000KP-ACI-4\"-C1F-1517")
("4\"-190F83845C586C4B291BC16A1D" "3000KP-ACI-4\"-C1F-1518")
("4\"-F75EE9E1309CCC4D579966BCDA" "3000KP-ACI-4\"-C1F-1519")
("4\"-C1E945B459837F4F8AE9C6D3B4" "3000KP-ACI-4\"-C1F-1520")
("4\"-65A5C7ACBE48AB4E54CB79F2E8" "3000KP-ACI-4\"-C1F-1521")
("4\"-6667357C5496744C5EDA5B859C" "3000KP-ACI-4\"-C1F-1522")
("4\"-7733BD2A1A27A7464A98BE1E38" "3000KP-ACI-4\"-C1F-1523")
("4\"-B236C705E179604EEDFA8B4C8C" "3000KP-ACI-4\"-C1F-1524")
("4\"-A5017F158E3EA34A93C8DE7E31" "3000KP-ACI-4\"-C1F-1525")
("4\"-D521F54B29B9DE439AC8E7C28D" "3000KP-ACI-4\"-C1F-1526")
("4\"-74D1102DBD6AAF411E6A94EE5E" "3000KP-ACI-4\"-C1F-1527")
("4\"-7BE595190F838445C589CB291E" "3000KP-ACI-4\"-C1F-1528")
("4\"-58D2858ED671794B825946DE2A" "3000KP-ACI-4\"-C1F-1529")
("4\"-DC23429DB61281426509CC47B4" "3000KP-ACI-4\"-C1F-1530")
("4\"-D7E4B475B6C8BD4BF59ACE65DE" "3000KP-ACI-4\"-C1F-1531")
("4\"-35BDA43324F248411639182AA5" "3000KP-ACI-4\"-C1F-1532")
("4\"-8EB8C0AA77F26E44D5BBBA8DC4" "3000KP-ACI-4\"-C1F-1533")
("4\"-E2326BB225C7054E1699FDEDEA" "3000KP-ACI-4\"-C1F-1534")
("4\"-8A3B7CDEB3C61F4B2FC84EEA6E" "3000KP-ACI-4\"-C1F-1535")
("4\"-59D8D9A2EDB2174E686ABF679C" "3000KP-ACI-4\"-C1F-1536")
("4\"-A38D4A85E2213E4CE7BA122F7C" "3000KP-ACI-4\"-C1F-1537")
("3\"-4FDF9CC23419DB461288269040" "3000KP-ACI-3\"-C1F-1538")
("2\"-5C3ACBEF4ABD1F48D39BDA4776" "3000KP-ACI-2\"-C1F-1539")
("3\"-8E6436B1736DB545F57A603334" "3000KP-ACI-3\"-C1F-1540")
("3\"-BDF9CC23419DB64128186504BB" "3000KP-ACI-3\"-C1F-1541")
("3\"-47A393A080427249479AB1588B" "3000KP-ACI-3\"-C1F-1542")
("3\"-219A46CEB54445413598274429" "3000KP-ACI-3\"-C1F-1543")
("2\"-3CB628637A551149B08B8F5854" "3000KP-ACI-2\"-C1F-1544")
("3\"-2A4FEA1DBF3DD945D48A7C891D" "3000KP-ACI-3\"-C1F-1545")
("3\"-CA1F6D5659AE5548BA3AD4985E" "3000KP-ACI-3\"-C1F-1546")
("3\"-1213DBD7BB012F47B94BF6E047" "3000KP-ACI-3\"-C1F-1547")
("3\"-D2EA3992B1CE6E42055A29769E" "3000KP-ACI-3\"-C1F-1548")
("2\"-4A691E8839AC9446667B13C005" "3000KP-ACI-2\"-C1F-1549")
("4\"-32E52E3611C9184B1A0AC511E4" "3000KP-ACI-4\"-C1F-1550")
("3\"-B3913256A225864F490941ADDD" "3000KP-ACI-3\"-C1F-1551")
("3\"-1CAC6AAE01E6A843DE5BE36C1D" "3000KP-ACI-3\"-C1F-1552")
("3\"-6E55D8D9A2ADB2417E6926BF62" "3000KP-ACI-3\"-C1F-1553")
("3\"-18701A1252BDED4F68A988CDEC" "3000KP-ACI-3\"-C1F-1554")
("4\"-164E9A09AED8C444CF3A2B3818" "3000KP-ACI-4\"-C1F-1555")
("4\"-75B6C8BDBF59BC4E65DB8A03F9" "3000KP-ACI-4\"-C1F-1556")
("4\"-BBBC8AC2A9EBC942A43BA1DAE2" "3000KP-ACI-4\"-C1F-1557")
("4\"-11CC58B4A4B15140E43A58A9C2" "3000KP-ACI-4\"-C1F-1558")
("4\"-4ABD5F8D79F2E847768913C515" "3000KP-ACI-4\"-C1F-1559")
("4\"-12F70953063158432EA99D2C2C" "3000KP-ACI-4\"-C1F-1560")
("4\"-D622F54B29BADE43AAD8E8C38E" "3000KP-ACI-4\"-C1F-1561")
("4\"-1D7AA9B64704484AA8092D88E7" "3000KP-ACI-4\"-C1F-1562")
("4\"-9D17B84C33B5A647F8BAED5B31" "3000KP-ACI-4\"-C1F-1563")
("4\"-149D414A923C35474D18029BD6" "3000KP-ACI-4\"-C1F-1564")
("4\"-66BCCA275FAA1A4BFE9B55D04C" "3000KP-ACI-4\"-C1F-1565")
("4\"-D7E4C476B6D8BD4CF59ACE65DE" "3000KP-ACI-4\"-C1F-1566")
("4\"-9B141A8889579E476B8A7E710A" "3000KP-ACI-4\"-C1F-1567")
("4\"-C2FC14EEAA36924829E9EDC218" "3000KP-ACI-4\"-C1F-1568")
("4\"-CF10499003A5D34CE479DBCBC8" "3000KP-ACI-4\"-C1F-1569")
("4\"-D092D234292B754285299541C5" "3000KP-ACI-4\"-C1F-1570")
("4\"-26A5A67EBA8ED44B34397C3369" "3000KP-ACI-4\"-C1F-1571")
("4\"-03F9BBBC4682654ABC9864E9A1" "3000KP-ACI-4\"-C1F-1572")
("4\"-0B56C57BE5951940F83A45C586" "3000KP-ACI-4\"-C1F-1573")
("4\"-BB280DC05A1CF745EE9B130ACC" "3000KP-ACI-4\"-C1F-1574")
("4\"-67E13C005674C14E945A459837" "3000KP-ACI-4\"-C1F-1575")
("4\"-77F26E5E6B3BED43D5F9547C13" "3000KP-ACI-4\"-C1F-1576")
("4\"-47DC56028A71FF4E1CE85DD3F0" "3000KP-ACI-4\"-C1F-1577")
("4\"-181A94174158334FF7AB7C6D37" "3000KP-ACI-4\"-C1F-1578")
("4\"-43276D8BDC055B4CF61AE8A13F" "3000KP-ACI-4\"-C1F-1579")
("4\"-B9A9B64608489A48F82BB8EB8C" "3000KP-ACI-4\"-C1F-1580")
("4\"-500B707AE9EAB440FD3890798B" "3000KP-ACI-4\"-C1F-1581")
("4\"-37DE143B16C21D479A9A646044" "3000KP-ACI-4\"-C1F-1582")
("3\"-9AB9153E8908AE428C89C33B6B" "3000KP-ACI-3\"-C1F-1583")
("1\"-24B475AA17FCBE449FBB64DD8E" "3000KP-ACI-1\"-C1F-1584")
("X\"-BA2C021499013A45D3CB574DCC" "3000KP-ACI-X\"-C1F-1585")
("3\"-6BA2CF214990134A5D3AE574DC" "3000KP-ACI-3\"-C1F-1586")
("3\"-CBD8682A6ABCA24A4FDA1DBF3D" "3000KP-ACI-3\"-C1F-1587")
("3\"-3CEFE179B599DE40D5993CD4CD" "3000KP-ACI-3\"-C1F-1588")
("3\"-558BA38D4985E14212DAD7BA01" "3000KP-ACI-3\"-C1F-1589")
("X\"-CB6A22AC19F9164D697B8EADED" "3000KP-ACI-X\"-C1F-1590")
("3\"-6E2054B29769E44A691B8839AC" "3000KP-ACI-3\"-C1F-1591")
("3\"-1499013A5D3CE5474DCABD8682" "3000KP-ACI-3\"-C1F-1592")
("3\"-A6ABCA2A4FEA1D4BF3DB95D48C" "3000KP-ACI-3\"-C1F-1593")
("3\"-7C891DCA1F6D56459AE958BA38" "3000KP-ACI-3\"-C1F-1594")
("3\"-D4985E1213DBD74BB018F7B94E" "3000KP-ACI-3\"-C1F-1595")
("X\"-F6E047D2EA39924B1CE9E2055B" "3000KP-ACI-X\"-C1F-1596")
("3\"-29769E4A691E88439ACA46667E" "3000KP-ACI-3\"-C1F-1597")
("4\"-907ECAE48EBD544CD7DB2E8ABA" "3000KP-ACI-4\"-C1F-1598")
("4\"-3ACE8BB12307CA45F17B154E3A" "3000KP-ACI-4\"-C1F-1599")
("2 1/2\"-3BD2A1A27E7A8E490BE8E37CEE" "3000KP-ACI-2 1/2\"-C1F-1600")
("3\"-A1F8935BDA433244F14A116331" "3000KP-ACI-3\"-C1F-1601")
("3\"-5D761D41D2500B4C47A993A040" "3000KP-ACI-3\"-C1F-1602")
("3\"-75BA1CF104990143A5D9CE474D" "3000KP-ACI-3\"-C1F-1603")
("4\"-44451E1A3D34524A3C7939637A" "3000KP-ACI-4\"-C1F-1604")
("4\"-22D928C1B1CD5241E54A29B9DE" "3000KP-ACI-4\"-C1F-1605")
("4\"-E669CA48E4A85E42223BCE8BB1" "3000KP-ACI-4\"-C1F-1606")
("4\"-DEC4861BC3BC144AEB7B66E8D9" "3000KP-ACI-4\"-C1F-1607")
("4\"-E7E2165C3A87AF44A798F8939B" "3000KP-ACI-4\"-C1F-1608")
("4\"-DA47778F24D1164785D8FA56C5" "3000KP-ACI-4\"-C1F-1609")
("4\"-E32C188137F6F74C4C0B4E5145" "3000KP-ACI-4\"-C1F-1610")
("4\"-1459BCF65DE8A143098A79579D" "3000KP-ACI-4\"-C1F-1611")
("4\"-337453A3CC6396448B6922AC19" "3000KP-ACI-4\"-C1F-1612")
("4\"-B5C2622F54B69B4AD33AAD4E7C" "3000KP-ACI-4\"-C1F-1613")
("4\"-E1696FDDDEA8A44C7CDBC4C610" "3000KP-ACI-4\"-C1F-1614")
("4\"-8EB9D1BB73B26A45A67BBA8ED4" "3000KP-ACI-4\"-C1F-1615")
("4\"-7E1F348F0364D248D42B8BBBC8" "3000KP-ACI-4\"-C1F-1616")
("4\"-D09DD23429DB714281299141C5" "3000KP-ACI-4\"-C1F-1617")
("4\"-43B6B7818BAFE64C42199D414A" "3000KP-ACI-4\"-C1F-1618")
("4\"-5EE9F130ACCCD5479369BCDA37" "3000KP-ACI-4\"-C1F-1619")
("4\"-D8349348726DD649C5B9C2A254" "3000KP-ACI-4\"-C1F-1620")
("4\"-51726769E466914E8839AC9422" "3000KP-ACI-4\"-C1F-1621")
("4\"-57247B448664B44DD84A759C77" "3000KP-ACI-4\"-C1F-1622")
("3\"-EE7AD6C6D37331465C7ACBE44B" "3000KP-ACI-3\"-C1F-1623")
("4\"-7A2C5A46BEB5334340D892C234" "3000KP-ACI-4\"-C1F-1624")
("1\"-91A4ED90DAE2CC484C39B6B780" "3000KP-ACI-1\"-C1F-1625")
("1 1/4\"-886BA2802145A141475B39E530" "3000KP-ACI-1 1/4\"-C1F-1626")
("4\"-CEEE0B9B598DEF4C5978CD4CD2" "3000KP-ACI-4\"-C1F-1627")
("2 1/2\"-27BDD18701AC2542B9AAB68AF8" "3000KP-ACI-2 1/2\"-C1F-1628")
("3\"-8C9A8F821B8EB84C0AA97F26E4" "3000KP-ACI-3\"-C1F-1629")
("3\"-D5BEBA8DD4E24346BC396D715F" "3000KP-ACI-3\"-C1F-1630")
("3\"-27961EEE0B9B5C48DEFA5D721D" "3000KP-ACI-3\"-C1F-1631")
("3\"-41D2500B707AF94EAB48FD3290" "3000KP-ACI-3\"-C1F-1632")
("4\"-798BC188BEC6A046CA7844451E" "3000KP-ACI-4\"-C1F-1633")
("1 1/4\"-19DD34529EC72248237A151C5C" "3000KP-ACI-1 1/4\"-C1F-1634")
("2 1/2\"-58BA38D4985E12413DBB7BB012" "3000KP-ACI-2 1/2\"-C1F-1635")
("3\"-F7B94EF6E047D24EA39A2B1CE6" "3000KP-ACI-3\"-C1F-1636")
("3\"-E2055B29769E4A4691EA839AC9" "3000KP-ACI-3\"-C1F-1637")
("3\"-46667E13C0056744C1EA45B459" "3000KP-ACI-3\"-C1F-1638")
("3\"-837EE7AD7C6D3B4375A9C7ACBE" "3000KP-ACI-3\"-C1F-1639")
("4\"-48BBE64DD79F2E48777A468D55" "3000KP-ACI-4\"-C1F-1640")
("1 1/4\"-A785C6FE95B96A4D8849CF3B2B" "3000KP-ACI-1 1/4\"-C1F-1641")
("3\"-468D55A785C6FE495B99AD8844" "3000KP-ACI-3\"-C1F-1642")
("2\"-3334F249216341492BA9285269" "3000KP-ACI-2\"-C1F-1643")
("3\"-CF3B2B38C876BA42C028499013" "3000KP-ACI-3\"-C1F-1644")
("2 1/2\"-A4FEA1DBF3DD954D48C9C891DC" "3000KP-ACI-2 1/2\"-C1F-1645")
("1\"-2EA3992B1CE6E24055B89769E4" "3000KP-ACI-1\"-C1F-1646")
("2\"-CB8EB8C0AA62A245A4996EAA8D" "3000KP-ACI-2\"-C1F-1647")
("1 1/4\"-A691E8839AC9464667E83C0056" "3000KP-ACI-1 1/4\"-C1F-1648")
("3\"-45B459837EE7AD47C6D9B375A5" "3000KP-ACI-3\"-C1F-1649")
("2 1/2\"-92C2CE6E2065B34A76AB4A691E" "3000KP-ACI-2 1/2\"-C1F-1650")
("2\"-BB6CD1D7999A2446F43A9A8F42" "3000KP-ACI-2\"-C1F-1651")
("1 1/4\"-C78E78CB6A33AD42A0986E7A8D" "3000KP-ACI-1 1/4\"-C1F-1652")
("3\"-C7ACBE48BBE64D4D79F8E87778" "3000KP-ACI-3\"-C1F-1653")
("2 1/2\"-A5D3CE574DCCBD48682A6ABCA2" "3000KP-ACI-2 1/2\"-C1F-1654")
("2\"-A1F6D5659AE5584BA38B4985E1" "3000KP-ACI-2\"-C1F-1655")
("1 1/4\"-213DBD7BB012F74B94EB6E047D" "3000KP-ACI-1 1/4\"-C1F-1656")
("8\"-74C1E945B4598347EE7AD7C6D3" "3940KP-ACI-8\"-C1F-018")
("4\"-B375A5C7ACBE484BBE69DD79F2" "3940KP-ACI-4\"-C1F-019")
("4\"-E87778468D55A7485C6BE95B96" "3940KP-ACI-4\"-C1F-020")
("4\"-AD8844CF3B2B384C876AA2C021" "3940KP-ACI-4\"-C1F-021")
("4\"-499013A5D3CE5744DCCAD8682A" "3940KP-ACI-4\"-C1F-022")
("4\"-6ABCA2A4FEA1DB4F3DDA5D48C7" "3940KP-ACI-4\"-C1F-023")
("4\"-C891DCA1F6D56549AE598BA38D" "3940KP-ACI-4\"-C1F-024")
("4\"-4985E1213DBD7B4B012B7B94EF" "3940KP-ACI-4\"-C1F-025")
("4\"-43F6304722EA294D2B1AD63205" "3940KP-ACI-4\"-C1F-026")
("4\"-806D0E238EE2534C17C91D7AAA" "3940KP-ACI-4\"-C1F-027")
("4\"-B7571449AB80534D89FA9D17B7" "3940KP-ACI-4\"-C1F-028")
("4\"-3B32A5A67F7B9E4D5B38F38C3F" "3940KP-ACI-4\"-C1F-029")
("4\"-39812B2463CFFE418AC999EF0D" "3940KP-ACI-4\"-C1F-030")
("4\"-5A73DD4CE32C184813786F7C4C" "3940KP-ACI-4\"-C1F-031")
("4\"-0E4E614648D24547ED69138B82" "3940KP-ACI-4\"-C1F-032")
("4\"-1102CE16EE301E46E888E52F47" "3940KP-ACI-4\"-C1F-033")
("4\"-22DD68C5B5C25241E54A69A9D3" "3940KP-ACI-4\"-C1F-034")
("4\"-399C4D7B68D1D745556802B4E4" "3940KP-ACI-4\"-C1F-035")
("4\"-564B4D874A748B4663E9D26051" "3940KP-ACI-4\"-C1F-036")
("4\"-2A7649806D0E2348EE293C17C3" "3940KP-ACI-4\"-C1F-037")
("4\"-1D7AAAB75714494AB8093D89F8" "3940KP-ACI-4\"-C1F-038")
("4\"-9D17B73B32A5A647F7BAED5B31" "3940KP-ACI-4\"-C1F-039")
("4\"-F38C3F39812B24463CFBE18AC5" "3940KP-ACI-4\"-C1F-040")
("4\"-99EF0D5A73DD4C4E32C8881370" "3940KP-ACI-4\"-C1F-041")
("4\"-6F7C4C0E4E6146448D2957ED67" "3940KP-ACI-4\"-C1F-042")
("4\"-138B821102CE164EE308E6E882" "3940KP-ACI-4\"-C1F-043")
("4\"-E52F4722DD68C54B5C2921E54A" "3940KP-ACI-4\"-C1F-044")
("4\"-69A9D3399C4D7B468D1B755562" "3940KP-ACI-4\"-C1F-045")
("4\"-02B4E4564B4D8744A74AB663E6" "3940KP-ACI-4\"-C1F-046")
("6\"-D260512A76498046D0E838EE25" "3940KP-ACI-6\"-C1F-047")
("8\"-3C17C31D7AAAB74571499AB805" "3940KP-ACI-8\"-C1F-048")
("6\"-ED5B31F38C3F394812B8463CFF" "3940KP-ACI-6\"-C1F-050")
("6\"-E18AC599EF0D5A473DD9CE32C1" "3940KP-ACI-6\"-C1F-051")
("6\"-8813706F7C4C0E44E619648D24" "3940KP-ACI-6\"-C1F-052")
("6\"-57ED67138B8211402CE86EE301" "3940KP-ACI-6\"-C1F-053")
("6\"-E6E882E52F47224DD68A5B5C25" "3940KP-ACI-6\"-C1F-054")
("8\"-21E54A69A9D33949C4D9B68D1D" "3940KP-ACI-8\"-C1F-055")
("4\"-75556202B4E45644B4DA74A748" "3940KP-ACI-4\"-C1F-056")
("4\"-B663E6D260512A47649A06D0E2" "3940KP-ACI-4\"-C1F-057")
("4\"-38EE253C17C31D47AAAA757144" "3940KP-ACI-4\"-C1F-058")
("4\"-9AB8053D89F89D417B79B32A5A" "3940KP-ACI-4\"-C1F-059")
("4\"-67F7B9ED5B31F348C3F99812B2" "3940KP-ACI-4\"-C1F-060")
("4\"-463CFFE18AC5994EF0D9A73DD4" "3940KP-ACI-4\"-C1F-061")
("4\"-CE32C18813706F47C4C8E4E614" "3940KP-ACI-4\"-C1F-062")
("4\"-648D2457ED671348B828102CE1" "3940KP-ACI-4\"-C1F-063")
("4\"-6EE301E6E882E542F4782DD68C" "3940KP-ACI-4\"-C1F-064")
("4\"-5B5C2521E54A694A9D3999C4D7" "3940KP-ACI-4\"-C1F-065")
("4\"-B68D1D755562024B4E4964B4D8" "3940KP-ACI-4\"-C1F-066")
("4\"-74A748B663E6D2460518A76498" "3940KP-ACI-4\"-C1F-067")
("6\"-3D89F89D17B73B432A5A67F7B9" "3940KP-ACI-6\"-C1F-049")
("4\"-37EE7AD7C6D3B3475A5A7ACBE4" "3940KP-ACI-4\"-C1F-082")
("4\"-17E10349F0364D428D48E8BBBC" "3940KP-ACI-4\"-C1F-083")
("1\"-CAC699EF1D5A834DE5DB36C1C8" "3940KP-ACI-1\"-C1F-084")
("2 1/2\"-1870A0BC5C1E434A18698D2858" "3940KP-ACI-2 1/2\"-C1F-085")
("1\"-ED67179B8255464DF2ABE4553A" "3940KP-ACI-1\"-C1F-086")
("2 1/2\"-FC8339348726DD468C5A5C2925" "3940KP-ACI-2 1/2\"-C1F-087")
("1\"-494B69B9D379AC443BC98D1D76" "3940KP-ACI-1\"-C1F-088")
("2 1/2\"-657246B448564B44DD79A759C7" "3940KP-ACI-2 1/2\"-C1F-089")
("1\"-EE293C1BD363CA4AAB7971949A" "3940KP-ACI-1\"-C1F-090")
("4\"-8BBE64DD79F2E847778968D55A" "3940KP-ACI-4\"-C1F-091")
("4\"-785C6FE95B96AD48844AF3B2B3" "3940KP-ACI-4\"-C1F-092")
("3\"-8C876BA2C0214949013A5D3CE5" "3940KP-ACI-3\"-C1F-093")
("3\"-96D71BA7CA7BE9495198483845" "3940KP-ACI-3\"-C1F-094")
("2 1/2\"-74DCCBD8682A6A4BCA2A4FEA1D" "3940KP-ACI-2 1/2\"-C1F-095")
("4\"-B067ACB49E5B96403329ECF8CC" "3940KP-ACI-4\"-C1F-068")
("2 1/2\"-13318DA611702649F4FA4AA3D3" "3940KP-ACI-2 1/2\"-C1F-069")
("2 1/2\"-EF7F3176C4B97B415B8A219A4A" "3940KP-ACI-2 1/2\"-C1F-070")
("2 1/2\"-9769E4A691E88349AC996667E1" "3940KP-ACI-2 1/2\"-C1F-071")
("4\"-3C005674C1E9454B459A37EE7A" "3940KP-ACI-4\"-C1F-072")
("3\"-D7C6D3B375A5C74ACBE98BBE64" "3940KP-ACI-3\"-C1F-073")
("2 1/2\"-DD79F2E877784648D55A785C6F" "3940KP-ACI-2 1/2\"-C1F-074")
("3\"-E95B96AD8844CF43B2B98C876B" "3940KP-ACI-3\"-C1F-075")
("2\"-A2C021499013A54D3CE974DCCB" "3940KP-ACI-2\"-C1F-076")
("2\"-D8682A6ABCA2A44FEA1BBF3DD9" "3940KP-ACI-2\"-C1F-077")
("2\"-5D48C7C891DCA14F6D5959AE55" "3940KP-ACI-2\"-C1F-078")
("3\"-8BA38D4985E12143DBD9BB012F" "3940KP-ACI-3\"-C1F-079")
("2 1/2\"-7B94EF6E047D2E4A3998B1CE6E" "3940KP-ACI-2 1/2\"-C1F-080")
("2\"-6667E13C0056744C1E995B4598" "3940KP-ACI-2\"-C1F-081")
("6\"-1F6D5659AE558B4A38D9985E12" "3940KP-ACI-6\"-C1F-110")
("4\"-C886BA28021459411479E38E53" "3940KP-ACI-4\"-C1F-111")
("1\"-09CCCD979266BC4DA279FAA1AB" "3940KP-ACI-1\"-C1F-112")
("2 1/2\"-F39D95D54C7C89429CB807D532" "3940KP-ACI-2 1/2\"-C1F-113")
("1\"-5AE524BA34D46845E22839BD7B" "3940KP-ACI-1\"-C1F-114")
("2 1/2\"-B012F7B95E06E1454E3AA35928" "3940KP-ACI-2 1/2\"-C1F-115")
("1\"-29E6E2061736764AF46991F893" "3940KP-ACI-1\"-C1F-116")
("2 1/2\"-5ADA42324E138140523881A941" "3940KP-ACI-2 1/2\"-C1F-117")
("1\"-7415833FF8AE7C46D4793166C7" "3940KP-ACI-1\"-C1F-118")
("4\"-13DBD7BB012F7B494EF9E047D2" "3940KP-ACI-4\"-C1F-119")
("4\"-EA3992B1CE6E20455B2A769E4A" "3940KP-ACI-4\"-C1F-120")
("3\"-691E8839AC9466467E19C00567" "3940KP-ACI-3\"-C1F-121")
("3\"-E0E378EE293C1B4D363AAAAB75" "3940KP-ACI-3\"-C1F-122")
("2 1/2\"-4C1E945B4598374EE7AB7C6D3B" "3940KP-ACI-2 1/2\"-C1F-123")
("4\"-BF3DD95D48C7C8491DCA1F6D56" "3940KP-ACI-4\"-C1F-096")
("2 1/2\"-59AE558BA38D49485E1813DBD7" "3940KP-ACI-2 1/2\"-C1F-097")
("2 1/2\"-BB012F7B94EF6E4047D8EA3992" "3940KP-ACI-2 1/2\"-C1F-098")
("2 1/2\"-B1CE6E2055B297469E4A691E88" "3940KP-ACI-2 1/2\"-C1F-099")
("4\"-39AC946667E13C4005694C1E94" "3940KP-ACI-4\"-C1F-100")
("3\"-5B459837EE7AD74C6D3A375A5C" "3940KP-ACI-3\"-C1F-101")
("2 1/2\"-7ACBE48BBE64DD479F2B877784" "3940KP-ACI-2 1/2\"-C1F-102")
("3\"-68D55A785C6FE945B96AD8844C" "3940KP-ACI-3\"-C1F-103")
("2\"-F3B2B38C876BA24C021999013A" "3940KP-ACI-2\"-C1F-104")
("2\"-5D3CE574DCCBD84682A9ABCA2A" "3940KP-ACI-2\"-C1F-105")
("2\"-352BEEDF79B4884DEEC9962CC3" "3940KP-ACI-2\"-C1F-106")
("3\"-0265F4BB46A3934AF7F9172847" "3940KP-ACI-3\"-C1F-107")
("2 1/2\"-97B1578A219A464BEB59435024" "3940KP-ACI-2 1/2\"-C1F-108")
("2\"-4FEA1DBF3DD95D448C7A891DCA" "3940KP-ACI-2\"-C1F-109")
("6\"-D79F2E877784684D55A985C6FE" "3940KP-ACI-6\"-C1F-138")
("4\"-E80B123071A54046415A33EA3A" "3940KP-ACI-4\"-C1F-139")
("1\"-D2C2DE732165C34ACBEB4ABD1F" "3940KP-ACI-1\"-C1F-140")
("2 1/2\"-8D39FDA477683143C119675C1E" "3940KP-ACI-2 1/2\"-C1F-141")
("1\"-A55B46AD484F8E4E72794B475B" "3940KP-ACI-1\"-C1F-142")
("2 1/2\"-A18FCBF590CE654DE8E83F9BCB" "3940KP-ACI-2 1/2\"-C1F-143")
("1\"-D468266ABCA2644E9A1AAED8C5" "3940KP-ACI-1\"-C1F-144")
("2 1/2\"-5D04C2B3919CA04B2C18149E11" "3940KP-ACI-2 1/2\"-C1F-145")
("1\"-4B933DF574ECCC4D9BD9AAFCDA" "3940KP-ACI-1\"-C1F-146")
("4\"-95B96AD8844CF34B2B3AC876BA" "3940KP-ACI-4\"-C1F-147")
("4\"-2C021499013A5D43CE594DCCBD" "3940KP-ACI-4\"-C1F-148")
("3\"-8682A6ABCA2A4F4EA1DAF3DD95" "3940KP-ACI-3\"-C1F-149")
("3\"-D48C7C891DCA1F46D5699AE558" "3940KP-ACI-3\"-C1F-150")
("2 1/2\"-BA38D4985E12134DBD7AB012F7" "3940KP-ACI-2 1/2\"-C1F-151")
("4\"-299EBC91A43DA14DAE2AC88147" "3940KP-ACI-4\"-C1F-124")
("2 1/2\"-0607C1CCA0E6144658DB458E92" "3940KP-ACI-2 1/2\"-C1F-125")
("2 1/2\"-7139B821102DBD46EAF81E6F84" "3940KP-ACI-2 1/2\"-C1F-126")
("2 1/2\"-375A5C7ACBE48B4BE64BD79F2E" "3940KP-ACI-2 1/2\"-C1F-127")
("4\"-87778468D55A7845C6FB95B96A" "3940KP-ACI-4\"-C1F-128")
("3\"-D8844CF3B2B38C4876BA2C0214" "3940KP-ACI-3\"-C1F-129")
("2 1/2\"-99013A5D3CE5744DCCBB8682A6" "3940KP-ACI-2 1/2\"-C1F-130")
("3\"-ABCA2A4FEA1DBF43DD99D48C7C" "3940KP-ACI-3\"-C1F-131")
("2\"-891DCA1F6D56594AE55ABA38D4" "3940KP-ACI-2\"-C1F-132")
("2\"-985E1213DBD7BB4012F9B94EF6" "3940KP-ACI-2\"-C1F-133")
("2\"-E047D2EA3992B14CE6E8055B29" "3940KP-ACI-2\"-C1F-134")
("3\"-769E4A691E88394AC949667E13" "3940KP-ACI-3\"-C1F-135")
("2 1/2\"-C005674C1E945B4459897EE7AD" "3940KP-ACI-2 1/2\"-C1F-136")
("2\"-7C6D3B375A5C7A4CBE4ABBE64D" "3940KP-ACI-2\"-C1F-137")
("2 1/2\"-667E13C005674C41E949B45983" "3000KP-ACI-2 1/2\"-C1F-1291")
("3\"-7EE7AD7C6D3B3745A5C9ACBE48" "3000KP-ACI-3\"-C1F-1291")
("4\"-BBE64DD57D0C654546296A3385" "3000KP-ACI-4\"-C1F-1292")
("3\"-53A4CC739648B64622AA19F916" "3000KP-ACI-3\"-C1F-1293")
("3\"-965498EADFD2774DE189B1AC25" "3000KP-ACI-3\"-C1F-1294")
("4\"-2BAA9B646084894A8F88DB8EB9" "3000KP-ACI-4\"-C1F-1295")
("2\"-D1BA73B26A5A674EBA8BD4B343" "3000KP-ACI-2\"-C1F-1296")
("1\"-78C3369715B27643CEEB0B9B59" "3000KP-ACI-1\"-C1F-1297")
("2 1/2\"-8DEFD5972CD4CD425B0A8077F9" "3000KP-ACI-2 1/2\"-C1F-1298")
("3\"-EAB4CFD329075447C2897EC661" "3000KP-ACI-3\"-C1F-1298")
("2 1/2\"-68A714445CE1AD4D34589EC723" "3000KP-ACI-2 1/2\"-C1F-1299")
("1\"-9237615CC58B4A44B1985383A5" "3000KP-ACI-1\"-C1F-1300")
("2 1/2\"-8A9C2689C32AB547D0C9554624" "3000KP-ACI-2 1/2\"-C1F-0971")
("3\"-6A338553A4CC7349648A6622AC" "3000KP-ACI-3\"-C1F-0972")
("3\"-19F916965498EA4DFD297DE183" "3000KP-ACI-3\"-C1F-0973")
("2\"-B1AC252BAA9B6446084A9A8F82" "3000KP-ACI-2\"-C1F-0974")
("2 1/2\"-DB8EB9D1BA73B246A5A97EBA8E" "3000KP-ACI-2 1/2\"-C1F-0975")
("2 1/2\"-D4B34378C33697415B2963CEEE" "3000KP-ACI-2 1/2\"-C1F-0976")
("2 1/2\"-B94EF6E047D2EA43992A1CE6E2" "3000KP-ACI-2 1/2\"-C1F-1033")
("3\"-055B29769E4A6941E8899AC946" "3000KP-ACI-3\"-C1F-1034")
("3\"-62F2BEE4563BFD4834A948B262" "3000KP-ACI-3\"-C1F-1098")
("2\"-2A2194956E6A8D4C4A2BE27B3E" "3000KP-ACI-2\"-C1F-1099")
("2 1/2\"-28701A1352BEED4F79B988DEEC" "3000KP-ACI-2 1/2\"-C1F-1100")
("2 1/2\"-4972CC3CD21BF747F26B5E6B3B" "3000KP-ACI-2 1/2\"-C1F-1101")
("4\"-7EC66168A7144445CE1ADD3452" "3000KP-ACI-4\"-C1F-1301")
("3\"-9EC7239237615C4C58B9A4B191" "3000KP-ACI-3\"-C1F-1303")
("1\"-5383A58A9C26894C32AA57D0C6" "3000KP-ACI-1\"-C1F-1304")
("3\"-5546246A3385534A4CC939648B" "3000KP-ACI-3\"-C1F-1305")
("2\"-6622AC19F9169645498BADFD27" "3000KP-ACI-2\"-C1F-1306")
("1\"-7DE183B1AC252B4AA9B9460848" "3000KP-ACI-1\"-C1F-1307")
("3\"-9A8F82DB8EB9D14BA73A26A5A6" "3000KP-ACI-3\"-C1F-1308")
("3\"-7EBA8ED4B343784C336A715B27" "3000KP-ACI-3\"-C1F-1309")
("3\"-63CEEE0B9B598D4EFD5A72CD4C" "3000KP-ACI-3\"-C1F-1310")
("2 1/2\"-D25B0C8077F9EA4B4CFB329075" "3000KP-ACI-2 1/2\"-C1F-1311")
("3\"-47C2847EC661684A714945CE1A" "3000KP-ACI-3\"-C1F-1311")
("4\"-DD34529EC72392437619CC58B4" "3000KP-ACI-4\"-C1F-1388")
("4\"-A4B1915383A58A49C26A9C32AB" "3000KP-ACI-4\"-C1F-1389")
("4\"-57D0C65546246A4338593A4CC7" "3000KP-ACI-4\"-C1F-1390")
("4\"-39648B6622AC194F916A65498E" "3000KP-ACI-4\"-C1F-1391")
("3\"-ADFD277DE183B14AC258BAA9B6" "3000KP-ACI-3\"-C1F-0977")
("3\"-4608489A8F82DB48EB9B1BA73B" "3000KP-ACI-3\"-C1F-0978")
("2\"-26A5A67EBA8ED44B34398C3369" "3000KP-ACI-2\"-C1F-0979")
("3\"-715B2763CEEE0B49B59ADEFD59" "3000KP-ACI-3\"-C1F-0980")
("3\"-72CD4CD25B0C80477F9BAB4CFD" "3000KP-ACI-3\"-C1F-0981")
("3\"-32907547C2847E4C66198A7144" "3000KP-ACI-3\"-C1F-0982")
("3\"-45CE1ADD34529E4C723A237615" "3000KP-ACI-3\"-C1F-0983")
("3\"-0B9B598DEFD59742CD4AD25B0C" "3000KP-ACI-3\"-C1F-1035")
("3\"-8077F9EAB4CFD342907947C284" "3000KP-ACI-3\"-C1F-1036")
("3\"-6495B69BAD38AA4D53CA79E1D7" "3000KP-ACI-3\"-C1F-1102")
("3\"-DDDEACE4BB1DEB43C65BB2FC14" "3000KP-ACI-3\"-C1F-1103")
("2\"-EEAA3692829E3E4DC21A3687AF" "3000KP-ACI-2\"-C1F-1104")
("3\"-06791B4935BDA443324BCF81C1" "3000KP-ACI-3\"-C1F-1105")
("3\"-23181A65174269444FB9AE3D3E" "3000KP-ACI-3\"-C1F-1106")
("4\"-3A4CC739648B66422AC89F9169" "3000KP-ACI-4\"-C1F-1315")
("2\"-65498EADFD277D4E183A1AC252" "3000KP-ACI-2\"-C1F-1316")
("1\"-BAA9B64608489A48F82BB8EB9D" "3000KP-ACI-1\"-C1F-1317")
("2 1/2\"-1BA73B26A5A67E4BA8EB4B3437" "3000KP-ACI-2 1/2\"-C1F-1318")
("3\"-8C3369715B27634CEEE8B9B598" "3000KP-ACI-3\"-C1F-1318")
("2\"-AB4CFD329075474C2849EC6616" "3000KP-ACI-2\"-C1F-1319")
("1\"-8A714445CE1ADD43452AEC7239" "3000KP-ACI-1\"-C1F-1320")
("2 1/2\"-237615CC58B4A44B1919383A58" "3000KP-ACI-2 1/2\"-C1F-1321")
("3\"-A9C2689C32AB574D0C69546246" "3000KP-ACI-3\"-C1F-1321")
("2 1/2\"-A338553A4CC7394648B9622AC1" "3000KP-ACI-2 1/2\"-C1F-1322")
("3\"-9F916965498EAD4FD279DE183B" "3000KP-ACI-3\"-C1F-1322")
("2\"-4B34378C33697145B2793CEEE0" "3000KP-ACI-2\"-C1F-0984")
("2 1/2\"-B9B598DEFD59724CD4CB25B0C8" "3000KP-ACI-2 1/2\"-C1F-0985")
("2\"-077F9EAB4CFD324907597C2847" "3000KP-ACI-2\"-C1F-0986")
("2 1/2\"-EC66168A7144454CE1ABD34529" "3000KP-ACI-2 1/2\"-C1F-0987")
("2 1/2\"-EC7239237615CC458B4A4B1915" "3000KP-ACI-2 1/2\"-C1F-0988")
("2 1/2\"-CC58B4A4B19153483A5AA9C268" "3000KP-ACI-2 1/2\"-C1F-1037")
("2 1/2\"-9C32AB57D0C655446249A33855" "3000KP-ACI-2 1/2\"-C1F-1038")
("2\"-1954387E5CED1246CD092AF5B2" "3000KP-ACI-2\"-C1F-1107")
("2 1/2\"-FC6998A535E3374897E91C67D6" "3000KP-ACI-2 1/2\"-C1F-1108")
("2\"-8CF6A62A11949546D699DC3A2E" "3000KP-ACI-2\"-C1F-1109")
("3\"-DE183B1AC252BA4A9B69608489" "3000KP-ACI-3\"-C1F-1325")
("4\"-A8F82DB8EB9D1B4A73B86A5A67" "3000KP-ACI-4\"-C1F-1326")
("3\"-3CEEE0B9B598DE4FD5992CD4CD" "3000KP-ACI-3\"-C1F-1327")
("3\"-7C2847EC66168A4714495CE1AD" "3000KP-ACI-3\"-C1F-1328")
("1\"-D34529EC72392347615AC58B4A" "3000KP-ACI-1\"-C1F-1329")
("3\"-4B1915383A58A94C268AC32AB5" "3000KP-ACI-3\"-C1F-1330")
("1\"-7D0C65546246A3438559A4CC73" "3000KP-ACI-1\"-C1F-1331")
("4\"-9648B6622AC19F4916995498EA" "3000KP-ACI-4\"-C1F-1332")
("1\"-DFD277DE183B1A4C252AAA9B64" "3000KP-ACI-1\"-C1F-1333")
("4\"-5CE1ADD34529EC47239837615C" "3000KP-ACI-4\"-C1F-0995")
("3\"-C58B4A4B19153843A58A9C2689" "3000KP-ACI-3\"-C1F-0996")
("3\"-C32AB57D0C655446246A338553" "3000KP-ACI-3\"-C1F-0997")
("3\"-A4CC739648B66242AC1AF91696" "3000KP-ACI-3\"-C1F-0998")
("3\"-5498EADFD277DE4183B8AC252B" "3000KP-ACI-3\"-C1F-0999")
("3\"-383A58A9C2689C432AB97D0C65" "3000KP-ACI-3\"-C1F-1042")
("3\"-546246A338553A44CC799648B6" "3000KP-ACI-3\"-C1F-1043")
("3\"-622AC19F9169654498EADFD277" "3000KP-ACI-3\"-C1F-1044")
("4\"-149D414A923C35474D18029AD6" "3000KP-ACI-4\"-C1F-1110")
("3\"-AAE11E6B84EE5D4F43D8992481" "3000KP-ACI-3\"-C1F-1111")
("4\"-B34378C33697154B2769CEEE0B" "3000KP-ACI-4\"-C1F-1334")
("3\"-9B598DEFD5972C4D4CD85B0C80" "3000KP-ACI-3\"-C1F-1335")
("4\"-77F9EAB4CFD329407549C2847E" "3000KP-ACI-4\"-C1F-1336")
("3\"-C66168A714445C4E1ADB34529E" "3000KP-ACI-3\"-C1F-1337")
("3\"-C7239237615CC548B4A9B19153" "3000KP-ACI-3\"-C1F-1338")
("1\"-83A58A9C2689C342AB59D0C655" "3000KP-ACI-1\"-C1F-1339")
("3\"-46246A338553A44CC73A648B66" "3000KP-ACI-3\"-C1F-1340")
("1\"-22AC19F9169654498EABFD277D" "3000KP-ACI-1\"-C1F-1341")
("3\"-E183B1AC252BAA49B64908489A" "3000KP-ACI-3\"-C1F-1342")
("1\"-8F82DB8EB9D1BA473B29A5A67E" "3000KP-ACI-1\"-C1F-1343")
("4\"-BA8ED4B34378C34369785B2763" "3000KP-ACI-4\"-C1F-1345")
("4\"-CEEE0B9B598DEF4D5978CD4CD2" "3000KP-ACI-4\"-C1F-1346")
("3\"-AA9B64608489A84F82DA8EB9D1" "3000KP-ACI-3\"-C1F-1019")
("4\"-BA73B26A5A67EB4A8ED9B34378" "3000KP-ACI-4\"-C1F-1020")
("3\"-C3369715B2763C4EEE0A9B598D" "3000KP-ACI-3\"-C1F-1021")
("3\"-EFD5972CD4CD254B0C8877F9EA" "3000KP-ACI-3\"-C1F-1022")
("3\"-B4CFD32907547C42847BC66168" "3000KP-ACI-3\"-C1F-1023")
("3\"-A714445CE1ADD344529BC72392" "3000KP-ACI-3\"-C1F-1024")
("3\"-37615CC58B4A4B41915983A58A" "3000KP-ACI-3\"-C1F-1050")
("4\"-9C2689C32AB57D40C65946246A" "3000KP-ACI-4\"-C1F-1051")
("3\"-338553A4CC7396448B6922AC19" "3000KP-ACI-3\"-C1F-1052")
("3\"-F916965498EADF4D277BE183B1" "3000KP-ACI-3\"-C1F-1053")
("3\"-AC252BAA9B646048489A8F82DB" "3000KP-ACI-3\"-C1F-1054")
("3\"-8EB9D1BA73B26A45A67BBA8ED4" "3000KP-ACI-3\"-C1F-1055")
("2 1/2\"-B1915383A58A9C42689A32AB57" "3000KP-ACI-2 1/2\"-C1F-1348")
("3\"-D0C65546246A3348553A4CC739" "3000KP-ACI-3\"-C1F-1348")
("3\"-FD277DE183B1AC4252BAA9B646" "3000KP-ACI-3\"-C1F-1349")
("3\"-A5A67EBA8ED4B344378A336971" "3000KP-ACI-3\"-C1F-1350")
("1\"-5B2763CEEE0B9B4598DBFD5972" "3000KP-ACI-1\"-C1F-1351")
("2 1/2\"-907547C2847EC646168A714445" "3000KP-ACI-2 1/2\"-C1F-1352")
("3\"-58B4A4B19153834A58AAC2689C" "3000KP-ACI-3\"-C1F-1353")
("1\"-32AB57D0C655464246A938553A" "3000KP-ACI-1\"-C1F-1354")
("4\"-498EADFD277DE1483B1AC252BA" "3000KP-ACI-4\"-C1F-1355")
("1\"-A9B64608489A8F482DBAEB9D1B" "3000KP-ACI-1\"-C1F-1356")
("2 1/2\"-4CFD32907547C24847EA66168A" "3000KP-ACI-2 1/2\"-C1F-0989")
("3\"-714445CE1ADD344529EA723923" "3000KP-ACI-3\"-C1F-0990")
("3\"-7615CC58B4A4B149153A3A58A9" "3000KP-ACI-3\"-C1F-0991")
("2 1/2\"-C2689C32AB57D04C65596246A3" "3000KP-ACI-2 1/2\"-C1F-0992")
("3\"-38553A4CC7396448B6682AC19F" "3000KP-ACI-3\"-C1F-0993")
("4\"-916965498EADFD4277DB183B1A" "3000KP-ACI-4\"-C1F-0994")
("2 1/2\"-5B0C8077F9EAB44CFD38907547" "3000KP-ACI-2 1/2\"-C1F-1039")
("3\"-C2847EC66168A7414449CE1ADD" "3000KP-ACI-3\"-C1F-1040")
("4\"-34529EC72392374615CA58B4A4" "3000KP-ACI-4\"-C1F-1041")
("2 1/2\"-4D5A3AEC2C4E24436B0936DB45" "3000KP-ACI-2 1/2\"-C1F-1112")
("3\"-E17960EEEFBDF44CC2EBC4D761" "3000KP-ACI-3\"-C1F-1113")
("3\"-C31D25FFBB46A3493A090ED329" "3000KP-ACI-3\"-C1F-1114")
("3\"-F82DB8EB9D1BA743B26A5A67EB" "3000KP-ACI-3\"-C1F-1357")
("4\"-A8ED4B34378C33469719B2763C" "3000KP-ACI-4\"-C1F-1357")
("3\"-2847EC66168A7144445AE1ADD3" "3000KP-ACI-3\"-C1F-1358")
("4\"-0C65546246A3384553A9CC7396" "3000KP-ACI-4\"-C1F-1359")
("3\"-D277DE183B1AC2452BAA9B6460" "3000KP-ACI-3\"-C1F-1360")
("4\"-8489A8F82DB8EB49D1BA73B26A" "3000KP-ACI-4\"-C1F-1360")
("3\"-D4CD25B0C8077F49EAB9CFD329" "3000KP-ACI-3\"-C1F-1381")
("1\"-07547C2847EC664168A914445C" "3000KP-ACI-1\"-C1F-1382")
("3\"-8B4A4B1915383A458A9A2689C3" "3000KP-ACI-3\"-C1F-1383")
("1\"-2AB57D0C655462446A398553A4" "3000KP-ACI-1\"-C1F-1384")
("3\"-98EADFD277DE1843B1AA252BAA" "3000KP-ACI-3\"-C1F-1385")
("4\"-A95B96AD88408F4372794C876B" "3000KP-ACI-4\"-C1F-1385")
("1\"-73B26A5A67EBA84ED4B94378C3" "3000KP-ACI-1\"-C1F-1386")
("4\"-369715B2763CEE4E0B9A598DEF" "3000KP-ACI-4\"-C1F-1387")
("3\"-C252BAA9B646084489AAF82DB8" "3000KP-ACI-3\"-C1F-1012")
("3\"-EB9D1BA73B26A54A67EAA8ED4B" "3000KP-ACI-3\"-C1F-1013")
("3\"-34378C3369715B42763AEEE0B9" "3000KP-ACI-3\"-C1F-1014")
("3\"-B598DEFD5972CD44CD29B0C807" "3000KP-ACI-3\"-C1F-1015")
("3\"-7F9EAB4CFD329047547A2847EC" "3000KP-ACI-3\"-C1F-1016")
("4\"-66168A714445CE41ADD94529EC" "3000KP-ACI-4\"-C1F-1017")
("3\"-7239237615CC584B4A4A191538" "3000KP-ACI-3\"-C1F-1018")
("3\"-3A58A9C2689C324AB57B0C6554" "3000KP-ACI-3\"-C1F-1047")
("3\"-6246A338553A4C4C739948B662" "3000KP-ACI-3\"-C1F-1048")
("3\"-2AC19F9169654948EADBD277DE" "3000KP-ACI-3\"-C1F-1049")
("3\"-D1315AA124B6E44DF589ECDCE9" "3000KP-ACI-3\"-C1F-1115")
("3\"-793B7BCDB3B51E4B2EB83EDA6E" "3000KP-ACI-3\"-C1F-1116")
("4\"-59D7D8A2EDB1174D676AAF669C" "3000KP-ACI-4\"-C1F-1117")
("3\"-A48E5A95F2223E4CE8CA12308C" "3000KP-ACI-3\"-C1F-1118")
("4\"-246A338553A4CC4739698B6622" "3000KP-ACI-4\"-C1F-1361")
("2 1/2\"-AC19F9169654984EADFB277DE1" "3000KP-ACI-2 1/2\"-C1F-1362")
("3\"-83B1AC252BAA9B46460A489A8F" "3000KP-ACI-3\"-C1F-1362")
("2 1/2\"-82DB8EB9D1BA734B26A9A67EBA" "3000KP-ACI-2 1/2\"-C1F-1363")
("3\"-8ED4B34378C33649715A2763CE" "3000KP-ACI-3\"-C1F-1363")
("2 1/2\"-EE0B9B598DEFD54972CB4CD25B" "3000KP-ACI-2 1/2\"-C1F-1364")
("3\"-0C8077F9EAB4CF4D32987547C2" "3000KP-ACI-3\"-C1F-1364")
("4\"-847EC66168A7144445CB1ADD34" "3000KP-ACI-4\"-C1F-1365")
("3\"-529EC72392376145CC5AB4A4B1" "3000KP-ACI-3\"-C1F-1366")
("3\"-915383A58A9C26489C38AB57D0" "3000KP-ACI-3\"-C1F-1367")
("4\"-C65546246A3385453A4AC73964" "3000KP-ACI-4\"-C1F-1368")
("1\"-8B6622AC19F91649654A8EADFD" "3000KP-ACI-1\"-C1F-1369")
("4\"-B9D1BA73B26A5A467EBA8ED4B3" "3000KP-ACI-4\"-C1F-1001")
("3\"-4378C3369715B24763CBEE0B9B" "3000KP-ACI-3\"-C1F-1002")
("2 1/2\"-F9EAB4CFD329074547C8847EC6" "3000KP-ACI-2 1/2\"-C1F-1004")
("2 1/2\"-6168A714445CE14ADD39529EC7" "3000KP-ACI-2 1/2\"-C1F-1005")
("2 1/2\"-239237615CC58B44A4B8915383" "3000KP-ACI-2 1/2\"-C1F-1006")
("2 1/2\"-A58A9C2689C32A4B57D8C65546" "3000KP-ACI-2 1/2\"-C1F-1045")
("4\"-84DE5DF47D2D924881B8CD5D1E" "3000KP-ACI-4\"-C1F-1119")
("3\"-54A29659E395804E782A9C9355" "3000KP-ACI-3\"-C1F-1120")
("3\"-56D02BFE4564B04D834A348726" "3000KP-ACI-3\"-C1F-1121")
("2 1/2\"-EE79D6B5C3A364494B6ABAD38A" "3000KP-ACI-2 1/2\"-C1F-1122")
("2 1/2\"-AD53CC79E1D766467359C44967" "3000KP-ACI-2 1/2\"-C1F-1123")
("3\"-598DEFD5972CD44CD25A0C8077" "3000KP-ACI-3\"-C1F-1124")
("4\"-1ADD34529EC72349237915CC58" "3000KP-ACI-4\"-C1F-1370")
("2 1/2\"-B4A4B1915383A548A9C8689C32" "3000KP-ACI-2 1/2\"-C1F-1371")
("3\"-AB57D0C655462446A33A553A4C" "3000KP-ACI-3\"-C1F-1371")
("2 1/2\"-C739648B6622AC419F98696549" "3000KP-ACI-2 1/2\"-C1F-1372")
("3\"-8EADFD277DE1834B1AC852BAA9" "3000KP-ACI-3\"-C1F-1372")
("2 1/2\"-B64608489A8F824DB8EA9D1BA7" "3000KP-ACI-2 1/2\"-C1F-1373")
("3\"-3B26A5A67EBA8E4D4B39378C33" "3000KP-ACI-3\"-C1F-1373")
("4\"-69715B2763CEEE40B9B998DEFD" "3000KP-ACI-4\"-C1F-1374")
("3\"-5972CD4CD25B0C48077B9EAB4C" "3000KP-ACI-3\"-C1F-1375")
("4\"-FD32907547C28447EC69168A71" "3000KP-ACI-4\"-C1F-1376")
("4\"-4445CE1ADD345249EC78392376" "3000KP-ACI-4\"-C1F-1378")
("4\"-689C32AB57D0C645546846A338" "3000KP-ACI-4\"-C1F-1379")
("1\"-553A4CC739648B46622AC19F91" "3000KP-ACI-1\"-C1F-1380")
("4\"-277DE183B1AC2542BAAAB64608" "3000KP-ACI-4\"-C1F-1007")
("2 1/2\"-A67EBA8ED4B343478C3969715B" "3000KP-ACI-2 1/2\"-C1F-1009")
("2 1/2\"-2763CEEE0B9B5948DEFB5972CD" "3000KP-ACI-2 1/2\"-C1F-1010")
("2 1/2\"-4CD25B0C8077F94EAB4AFD3290" "3000KP-ACI-2 1/2\"-C1F-1011")
("2 1/2\"-7547C2847EC661468A784445CE" "3000KP-ACI-2 1/2\"-C1F-1046")
("3\"-489A8F82DB8EB94D1BA93B26A5" "3000KP-ACI-3\"-C1F-1125")
("4\"-071A94174158334EE7AB6C6D37" "3000KP-ACI-4\"-C1F-1126")
("3\"-33165C7ACBE44A4BE5FAD79F2E" "3000KP-ACI-3\"-C1F-1127")
("2 1/2\"-87768424C5167745C6EA95B86A" "3000KP-ACI-2 1/2\"-C1F-1128")
("2 1/2\"-D88408E372734B4876BA28F204" "3000KP-ACI-2 1/2\"-C1F-1129")
("4\"-3B1AC252BAA9B644608989A8F8" "3940KP-ACI-4\"-C1F-166")
("4\"-2DB8EB9D1BA73B426A5A67EBA8" "3940KP-ACI-4\"-C1F-167")
("1\"-ED4B34378C33694715B8763CEE" "3940KP-ACI-1\"-C1F-168")
("2 1/2\"-E0B9B598DEFD59472CD9CD25B0" "3940KP-ACI-2 1/2\"-C1F-169")
("1\"-E811B7DA8CFAA646E15B4D5ADA" "3940KP-ACI-1\"-C1F-170")
("2 1/2\"-97DC3E2426BB2345C709E1696F" "3940KP-ACI-2 1/2\"-C1F-171")
("1\"-DEDFA8A4C8CDEC44C628C30D25" "3940KP-ACI-1\"-C1F-172")
("2 1/2\"-FEB7F6AE9E9B3F4EC32AF787BB" "3940KP-ACI-2 1/2\"-C1F-173")
("1\"-177ADB59F6BA71433348D09DC2" "3940KP-ACI-1\"-C1F-174")
("4\"-3419DB612812694041C9BB4D3E" "3940KP-ACI-4\"-C1F-175")
("4\"-0804276D4B98B145C8B91AA5AC" "3940KP-ACI-4\"-C1F-176")
("3\"-EB58889135E2274896D91B67C6" "3940KP-ACI-3\"-C1F-177")
("3\"-7BA59119C08E8F45D589C7E9CE" "3940KP-ACI-3\"-C1F-178")
("2 1/2\"-C8077F9EAB4CFD432909547C28" "3940KP-ACI-2 1/2\"-C1F-179")
("4\"-6965498EADFD2747DE1A3B1AC2" "3940KP-ACI-4\"-C1F-152")
("2 1/2\"-52BAA9B646084849A8FA2DB8EB" "3940KP-ACI-2 1/2\"-C1F-153")
("2 1/2\"-9D1BA73B26A5A647EBAAED4B34" "3940KP-ACI-2 1/2\"-C1F-154")
("2 1/2\"-378C3369715B27463CEBE0B9B5" "3940KP-ACI-2 1/2\"-C1F-155")
("4\"-98DEFD5972CD4C4D25B8C8077F" "3940KP-ACI-4\"-C1F-156")
("3\"-9EAB4CFD329075447C2A47EC66" "3940KP-ACI-3\"-C1F-157")
("2 1/2\"-168A714445CE1A4DD34929EC72" "3940KP-ACI-2 1/2\"-C1F-158")
("3\"-3F6304722DA29C42B1CB625387" "3940KP-ACI-3\"-C1F-159")
("2\"-E5CED126DD142B406B28C6999A" "3940KP-ACI-2\"-C1F-160")
("2\"-646F3389A7E42C478D7AC06A62" "3940KP-ACI-2\"-C1F-161")
("2\"-39237615CC58B44A4B1A15383A" "3940KP-ACI-2\"-C1F-162")
("3\"-58A9C2689C32AB457D0A655462" "3940KP-ACI-3\"-C1F-163")
("2 1/2\"-46A338553A4CC743964AB6622A" "3940KP-ACI-2 1/2\"-C1F-164")
("2\"-C19F916965498E4ADFD877DE18" "3940KP-ACI-2\"-C1F-165")
("4\"-B6622AC19F916946549AEADFD2" "3000KP-ACI-4\"-C1F-1657")
("3\"-739648B6622AC149F919965498" "3000KP-ACI-3\"-C1F-1658")
("4\"-EADFD277DE183B41AC292BAA9B" "3000KP-ACI-4\"-C1F-1659")
("1\"-64608489A8F82D4B8EBAD1BA73" "3000KP-ACI-1\"-C1F-1660")
("3\"-B26A5A67EBA8ED44B34978C336" "3000KP-ACI-3\"-C1F-1661")
("3\"-9715B2763CEEE04B9B5A8DEFD5" "3000KP-ACI-3\"-C1F-1662")
("1\"-9114B5E3DE574D4CCCDA793A6B" "3000KP-ACI-1\"-C1F-1663")
("3\"-A646F3389A7F424C78E98C06A6" "3000KP-ACI-3\"-C1F-1664")
("3\"-3A21A4956E6A8D4C4A28E27B3E" "3000KP-ACI-3\"-C1F-1665")
("1\"-BF39D95D44C7C84929CA1F7D53" "3000KP-ACI-1\"-C1F-1666")
("3\"-69E4A691E8838A4C936967E13C" "3000KP-ACI-3\"-C1F-1667")
("3\"-B40ED329F798BC4178ABC5A06C" "3000KP-ACI-3\"-C1F-1668")
("1\"-DDDEACE4CB1DEC44C658C30C14" "3000KP-ACI-1\"-C1F-1669")
("2 1/2\"-6633BD2A0917A7464998AE0E27" "3000KP-ACI-2 1/2\"-C1F-1670")
("3\"-DC8EB9D1BB73B246A5A97EBA8E" "3000KP-ACI-3\"-C1F-1671")
("4\"-907E0E348EF2544C27D92E8ABA" "3000KP-ACI-4\"-C1F-1672")
("3\"-C7571559AB91534E89FA9D18B8" "3000KP-ACI-3\"-C1F-1673")
("3\"-4C33B5A6808B9E4E5B48048D40" "3000KP-ACI-3\"-C1F-1674")
("3\"-3A822C3463D00F418AC9A9E01D" "3000KP-ACI-3\"-C1F-1675")
("3\"-47EC66168A7144445CE8ADD345" "3000KP-ACI-3\"-C1F-1676")
("3\"-29EC72392376154CC58A4A4B19" "3000KP-ACI-3\"-C1F-1677")
("3\"-15383A58A9C26849C32AB57D0C" "3000KP-ACI-3\"-C1F-1678")
("2 1/2\"-65546246A3385543A4CA739648" "3000KP-ACI-2 1/2\"-C1F-1679")
("3\"-77DE183B1AC2524BAA9A646084" "3000KP-ACI-3\"-C1F-1680")
("4\"-89A8F82DB8EB9D41BA79B26A5A" "3000KP-ACI-4\"-C1F-1681")
("3\"-67EBA8ED4B343748C3399715B2" "3000KP-ACI-3\"-C1F-1682")
("3\"-763CEEE0B9B5984DEFD9972CD4" "3000KP-ACI-3\"-C1F-1683")
("3\"-CD25B0C8077F9E4AB4CBD32907" "3000KP-ACI-3\"-C1F-1684")
("3\"-547C2847EC661648A719445CE1" "3000KP-ACI-3\"-C1F-1685")
("3\"-ADD34529EC72394237685CC58B" "3000KP-ACI-3\"-C1F-1686")
("3\"-4A4B1915383A584A9C2989C32A" "3000KP-ACI-3\"-C1F-1687")
("2 1/2\"-B57D0C655462464A338953A4CC" "3000KP-ACI-2 1/2\"-C1F-1688")
("4\"-CC739648B6622A4C19F9C2521F" "3000KP-ACI-4\"-C1F-1689")
("3\"-411E6F883E53F44722DB68C5B5" "3000KP-ACI-3\"-C1F-1690")
("4\"-C2521F54B69B9D4339AA4E7C68" "3000KP-ACI-4\"-C1F-1691")
("1\"-D1D76657202B4F44564A4D974A" "3000KP-ACI-1\"-C1F-1692")
("3\"-759C773E7D2616423A794A907E" "3000KP-ACI-3\"-C1F-1693")
("3\"-1FB2EC14EEA6E549D8DAA2EDB2" "3000KP-ACI-3\"-C1F-1694")
("1\"-917E1F349F03644D28D92E8BBB" "3000KP-ACI-1\"-C1F-1695")
("3\"-40D09DC23419DB461288269041" "3000KP-ACI-3\"-C1F-1696")
("3\"-91E8828AC9366647E13A0F5674" "3000KP-ACI-3\"-C1F-1697")
("1\"-5972CD4CD21B0848037B5E6B4C" "3000KP-ACI-1\"-C1F-1698")
("3\"-97D8EADED27BDD4186F8AC252B" "3000KP-ACI-3\"-C1F-1699")
("4\"-6767357C5496754C5EDA5B859C" "3000KP-ACI-4\"-C1F-1700")
("1\"-0E348EE253C17D432E8AAAB757" "3000KP-ACI-1\"-C1F-1701")
("2 1/2\"-5EB2EB03DD95D548C7CA92DDB1" "3000KP-ACI-2 1/2\"-C1F-1702")
("3\"-32E52E3611D9184C1A0AC511E4" "3000KP-ACI-3\"-C1F-1703")
("4\"-917E1F348FF3644D27D92E8BBB" "3000KP-ACI-4\"-C1F-1704")
("3\"-C868155ABC91644E990AAE28C8" "3000KP-ACI-3\"-C1F-1705")
("3\"-4C33B6B7818BAF4E6C48149D41" "3000KP-ACI-3\"-C1F-1706")
("3\"-3A923C3574D110428AC9AAE01E" "3000KP-ACI-3\"-C1F-1707")
("3\"-D32907547C28474EC66868A714" "3000KP-ACI-3\"-C1F-1708")
("3\"-445CE1ADD345294EC729923761" "3000KP-ACI-3\"-C1F-1709")
("3\"-5CC58B4A4B19154383A98A9C26" "3000KP-ACI-3\"-C1F-1710")
("2 1/2\"-89C32AB57D0C654546296A3385" "3000KP-ACI-2 1/2\"-C1F-1711")
("3\"-54B69B9D339AC44E7C6AD1D766" "3000KP-ACI-3\"-C1F-1712")
("4\"-57202B4F4564B44D974A759C77" "3000KP-ACI-4\"-C1F-1713")
("3\"-3E7D261623A7644A907B0E348E" "3000KP-ACI-3\"-C1F-1714")
("3\"-E253C17D32E8AA4AB7591549AB" "3000KP-ACI-3\"-C1F-1715")
("3\"-9153D89F89D17B484B39B5A67F" "3000KP-ACI-3\"-C1F-1716")
("3\"-8B9ED5B31F38D4403A882C2463" "3000KP-ACI-3\"-C1F-1717")
("3\"-C00F18AC699EF14D5A89DE5DE3" "3000KP-ACI-3\"-C1F-1718")
("3\"-2C1881470607C54C1E4B614658" "3000KP-ACI-3\"-C1F-1719")
("2 1/2\"-D2458ED67139B8421108DF26EE" "3000KP-ACI-2 1/2\"-C1F-1720")
("4\"-B5A67F8B9ED5B341F38B403A82" "3000KP-ACI-4\"-C1F-1721")
("3\"-4E7C68D1D766574202B9F4564B" "3000KP-ACI-3\"-C1F-1722")
("3\"-1D5A83DE5DE32C41881970607C" "3000KP-ACI-3\"-C1F-1723")
("3\"-BA77F26E5E5BEB4A8DD9E3437B" "3000KP-ACI-3\"-C1F-1724")
("3\"-6CC071AE9B130A48889935E727" "3000KP-ACI-3\"-C1F-1725")
("1\"-AB9193DC9FC9D14BB84A37B5A6" "3000KP-ACI-1\"-C1F-1726")
("3\"-5C1E4E614658D24458EB67139B" "3000KP-ACI-3\"-C1F-1727")
("3\"-2C2463C00F18AC4699EB1D5A83" "3000KP-ACI-3\"-C1F-1728")
("3\"-DE5DE32C18814740607A5C1E4E" "3000KP-ACI-3\"-C1F-1729")
("3\"-614658D2458ED647139A821102" "3000KP-ACI-3\"-C1F-1730")
("3\"-DF26EE411E6F8843E53B4722DD" "3000KP-ACI-3\"-C1F-1731")
("3\"-68C5B5C2521F544B69BAD339AC" "3000KP-ACI-3\"-C1F-1732")
("3\"-4D974A759C773E47D268623A76" "3000KP-ACI-3\"-C1F-1733")
("3\"-4A907E0E348EE2453C19D32E8A" "3000KP-ACI-3\"-C1F-1734")
("3\"-AAB7571549AB91453D8AF89D17" "3000KP-ACI-3\"-C1F-1735")
("3\"-B84B33B5A67F8B49ED5A31F38D" "3000KP-ACI-3\"-C1F-1736")
("3\"-403A822C2463C040F18AC699EF" "3000KP-ACI-3\"-C1F-1737")
("4\"-B5C2A25494B69B4AD37AAD43BC" "3000KP-ACI-4\"-C1F-1738")
("2\"-DD34529EC72382437619CC58B4" "3000KP-ACI-2\"-C1F-1739")
("3\"-C336D715F179604EEE0A9B5C8D" "3000KP-ACI-3\"-C1F-1740")
("1\"-AB8093DC9FC9D14BB73A36A5A6" "3000KP-ACI-1\"-C1F-1741")
("2\"-F743276D4BDCF145BCE819E4A1" "3000KP-ACI-2\"-C1F-1742")
("2\"-821102DF26EE4141E6FA83E53F" "3000KP-ACI-2\"-C1F-1743")
("2\"-D32E8AAAB75715449ABA153D89" "3000KP-ACI-2\"-C1F-1744")
("2\"-4722DD68C5B5C24521F94B69B9" "3000KP-ACI-2\"-C1F-1745")
("3\"-D339AC4E7C68D14D76697202B4" "3000KP-ACI-3\"-C1F-1746")
("2\"-F4564B4D974A7549C779E7D261" "3000KP-ACI-2\"-C1F-1747")
("2\"-623A764A907E0E4348EB253C17" "3000KP-ACI-2\"-C1F-1748")
("2\"-F89D17B84B33B54A67FAB9ED5B" "3000KP-ACI-2\"-C1F-1749")
("2\"-AC352BAA9B68A0488C9A80822B" "3000KP-ACI-2\"-C1F-1750")
("3\"-7DA7BE9955D14C43C49B997CB3" "3000KP-ACI-3\"-C1F-1751")
("2\"-58A9C2299C4D7B457D0A655562" "3000KP-ACI-2\"-C1F-1752")
("2\"-DF81C233182B654175299440B4" "3000KP-ACI-2\"-C1F-1753")
("2\"-48C6B791DCA0F64C465A9E558B" "3000KP-ACI-2\"-C1F-1754")
("4\"-29812B2363CEFE4079B998DEFD" "3000KP-ACI-4\"-C1F-1755")
("2\"-D31B66C67BA591419C0AE8F5D5" "3000KP-ACI-2\"-C1F-1756")
("3\"-86B6D8BDC059CC4F75EB8A1309" "3000KP-ACI-3\"-C1F-1757")
("1\"-3334F249116341492BA9285269" "3000KP-ACI-1\"-C1F-1758")
("2\"-DD992481718D1D4CA1F925659E" "3000KP-ACI-2\"-C1F-1759")
("2\"-70607C5C1E4E6144658B2458ED" "3000KP-ACI-2\"-C1F-1760")
("2\"-67139B821102DF426EE911E6F8" "3000KP-ACI-2\"-C1F-1761")
("3\"-83E53F4722DD684C5B5A2521F5" "3000KP-ACI-3\"-C1F-1762")
("2\"-4B69B9D339AC4E47C68B1D7665" "3000KP-ACI-2\"-C1F-1763")
("2\"-7202B4F4564B4D4974A959C773" "3000KP-ACI-2\"-C1F-1764")
("2\"-253C17D32E8AAA4B7578549AB9" "3000KP-ACI-2\"-C1F-1765")
("2\"-CB391ED16B2D1846F0A8241ADD" "3000KP-ACI-2\"-C1F-1766")
("3\"-AB3571549AB81543D89B89DC7B" "3000KP-ACI-3\"-C1F-1767")
("2\"-EE79D6C6C3A364495B7ABAE38A" "3000KP-ACI-2\"-C1F-1768")
("2\"-3B16C31D7AA9B644604989A804" "3000KP-ACI-2\"-C1F-1769")
("2\"-0B56C57BE5851940F83A45C586" "3000KP-ACI-2\"-C1F-1770")
("4\"-00F18AC699EF1D45A83BE5DE32" "3000KP-ACI-4\"-C1F-1771")
("3\"-E348EE253C17D342E8AAAB7571" "3000KP-ACI-3\"-C1F-1772")
("3\"-8C5B5C2521F54B469B9B339AC4" "3000KP-ACI-3\"-C1F-1773")
("3\"-874A748B663E6D4260582A7649" "3000KP-ACI-3\"-C1F-1774")
("3\"-D5B35478C447A8426B2A63CF0F" "3000KP-ACI-3\"-C1F-1775")
("3\"-EA8A477CDEB38641BC2AC14AEA" "3000KP-ACI-3\"-C1F-1776")
("3\"-4B32B5A67F7B9E4D5B38F38C40" "3000KP-ACI-3\"-C1F-1777")
("3\"-C42BB6BD0C69994A246B3389A7" "3000KP-ACI-3\"-C1F-1778")
("3\"-8CA50170154E3B4B46A9829F7F" "3000KP-ACI-3\"-C1F-1779")
("3\"-B9E91BE1F38CF043A828CD463C" "3000KP-ACI-3\"-C1F-1780")
("3\"-7778468D55A7854C6FEA6B96AD" "3000KP-ACI-3\"-C1F-1781")
("3\"-DD992582718D2D4DB10925769E" "3000KP-ACI-3\"-C1F-1782")
("3\"-A225C6F4E0685E4DDDEA8A4B7C" "3000KP-ACI-3\"-C1F-1783")
("3\"-674B5E985B859C4773E9E26162" "3000KP-ACI-3\"-C1F-1784")
("3\"-E733165C3ACBE044BBE809D39F" "3000KP-ACI-3\"-C1F-1785")
("3\"-63C00F1CAC699E4F1D5A83DE5D" "3000KP-ACI-3\"-C1F-1786")
("3\"-B039D95D54C7C84929DA107D53" "3000KP-ACI-3\"-C1F-1787")
("3\"-E27B3E29701A13452BEBEF79B4" "3000KP-ACI-3\"-C1F-1788")
("3\"-116775C2FA55B546A94A008AE7" "3000KP-ACI-3\"-C1F-1789")
("3\"-93A0804272947948B15A8F65DE" "3000KP-ACI-3\"-C1F-1790")
("3\"-139B821112DF264EE418E6F983" "3000KP-ACI-3\"-C1F-1791")
("3\"-B2FC14EEAA36924829E9EDC218" "3000KP-ACI-3\"-C1F-1792")
("3\"-7ACBE44ABE5F8D479F2B877683" "3000KP-ACI-3\"-C1F-1793")
("3\"-35D627886D71BA46CA7AE99519" "3000KP-ACI-3\"-C1F-1794")
("3\"-D261623A764A9047E1E948EF25" "3000KP-ACI-3\"-C1F-1795")
("3\"-1AE5B1FC688895435E387896E3" "3000KP-ACI-3\"-C1F-1796")
("3\"-4E9A19AE28C95D444C6A7919CA" "3000KP-ACI-3\"-C1F-1797")
("3\"-43918548D2847E4D67198B8245" "3000KP-ACI-3\"-C1F-1798")
("1\"-DE68A487CDEC48461BC9BC10AE" "3000KP-ACI-1\"-C1F-1799")
("3\"-E7C68D1D766572402B4B4564B4" "3000KP-ACI-3\"-C1F-1800")
("3\"-C1881470607C5C41E4E914658D" "3000KP-ACI-3\"-C1F-1801")
("3\"-2458ED67139B8241102BF26EE4" "3000KP-ACI-3\"-C1F-1802")
("3\"-11E6F883E53F47422DD98C5B5C" "3000KP-ACI-3\"-C1F-1803")
("3\"-2521F54B69B9D3439AC9E7C68D" "3000KP-ACI-3\"-C1F-1804")
("3\"-1D76657202B4F44564B9D974A7" "3000KP-ACI-3\"-C1F-1805")
("3\"-59C773E7D2616243A769A907E0" "3000KP-ACI-3\"-C1F-1806")
("3\"-549AB9153D89F849D17A84B33B" "3000KP-ACI-3\"-C1F-1807")
("3\"-5A67F8B9ED5B314F38D903A822" "3000KP-ACI-3\"-C1F-1808")
("3\"-C2463C00F18AC6499EF8D5A83D" "3000KP-ACI-3\"-C1F-1809")
("3\"-E5DE32C18814704607C9C1E4E6" "3000KP-ACI-3\"-C1F-1810")
("3\"-14658D2458ED674139BA21102D" "3000KP-ACI-3\"-C1F-1811")
("3\"-F26EE411E6F8834E53F9722DD6" "3000KP-ACI-3\"-C1F-1812")
("4\"-D974A759C773E74D261923A764" "3000KP-ACI-4\"-C1F-1813")
("2\"-84B33B5A67F8B94ED5B91F38D4" "3000KP-ACI-2\"-C1F-1814")
("2\"-D5A83DE5DE32C14881490607C5" "3000KP-ACI-2\"-C1F-1815")
("3\"-69BAD339AD4E7C468E1B766573" "3000KP-ACI-3\"-C1F-1816")
("1\"-D092C234192B654285299440C4" "3000KP-ACI-1\"-C1F-1817")
("4\"-C1E4E614658D24458ED97139B8" "3000KP-ACI-4\"-C1F-1818")
("2\"-A907E0E348EE2543C17B32E8AA" "3000KP-ACI-2\"-C1F-1819")
("2\"-AB7571549AB91543D89B89D17B" "3000KP-ACI-2\"-C1F-1820")
("3\"-03A822C2463C004F18AA699EF1" "3000KP-ACI-3\"-C1F-1821")
("2\"-58D2858ED671794B825946DF2A" "3000KP-ACI-2\"-C1F-1822")
("2\"-55ABC9164E9A094AED8A44CF3B" "3000KP-ACI-2\"-C1F-1823")
("3\"-93A0803272947948B1598B219A" "3000KP-ACI-3\"-C1F-1824")
("4\"-53C17D32E8AAAB47571949AB91" "3940KP-ACI-4\"-C1F-209")
("4\"-53D89F89D17B844B33B9A67F8B" "3940KP-ACI-4\"-C1F-210")
("4\"-9ED5B31F38D4034A822A2463C0" "3940KP-ACI-4\"-C1F-211")
("4\"-0F18AC699EF1D54A83DB5DE32C" "3940KP-ACI-4\"-C1F-212")
("4\"-1881470607C5C14E4E684658D2" "3940KP-ACI-4\"-C1F-213")
("4\"-458ED67139B8214102DB26EE41" "3940KP-ACI-4\"-C1F-214")
("4\"-1E6F883E53F47242DD6AC5B5C2" "3940KP-ACI-4\"-C1F-215")
("1\"-521F54B69B9D3349AC4B7C68D1" "3940KP-ACI-1\"-C1F-216")
("1\"-D76657202B4F45464B4B974A75" "3940KP-ACI-1\"-C1F-217")
("1\"-9C773E7D2616234A764A907E0E" "3940KP-ACI-1\"-C1F-218")
("1\"-348EE253C17D324E8AAAB75715" "3940KP-ACI-1\"-C1F-219")
("4\"-21102DF26EE4114E6F8A3E53F4" "3940KP-ACI-4\"-C1F-201")
("4\"-722DD68C5B5C25421F59B69B9D" "3940KP-ACI-4\"-C1F-202")
("4\"-339AC4E7C68D1D476659202B4F" "3940KP-ACI-4\"-C1F-203")
("4\"-4564B4D974A7594C773B7D2616" "3940KP-ACI-4\"-C1F-204")
("3\"-23A764A907E0E3448EE853C17D" "3940KP-ACI-3\"-C1F-205")
("3\"-32E8AAAB75715449AB9853D89F" "3940KP-ACI-3\"-C1F-206")
("3\"-1F38D403A822C24463C80F18AC" "3940KP-ACI-3\"-C1F-207")
("3\"-699EF1D5A83DE54DE32A188147" "3940KP-ACI-3\"-C1F-208")
("4\"-1E4E614658D24548ED69139B82" "3940KP-ACI-4\"-C1F-245")
("3\"-1102DF26EE411E46F889E53F47" "3940KP-ACI-3\"-C1F-246")
("4\"-22DD68C5B5C25241F54A69B9D3" "3940KP-ACI-4\"-C1F-247")
("4\"-39AC4E7C68D1D746657802B4F4" "3940KP-ACI-4\"-C1F-248")
("4\"-564B4D974A759C4773E9D26162" "3940KP-ACI-4\"-C1F-249")
("1\"-3A764A907E0E3448EE293C17D3" "3940KP-ACI-1\"-C1F-250")
("3\"-2E8AAAB75715494AB9193D89F8" "3940KP-ACI-3\"-C1F-251")
("1\"-9D17B84B33B5A647F8BAED5B31" "3940KP-ACI-1\"-C1F-252")
("3\"-F38D403A822C24463C08F18AC6" "3940KP-ACI-3\"-C1F-253")
("1\"-99EF1D5A83DE5D4E32C8881470" "3940KP-ACI-1\"-C1F-254")
("3\"-607C5C1E4E6146458D2958ED67" "3940KP-ACI-3\"-C1F-255")
("1\"-139B821102DF264EE418E6F883" "3940KP-ACI-1\"-C1F-256")
("3\"-E53F4722DD68C54B5C2921F54B" "3940KP-ACI-3\"-C1F-257")
("3\"-69B9D339AC4E7C468D1B766572" "3940KP-ACI-3\"-C1F-258")
("3\"-02B4F4564B4D9744A75AC773E7" "3940KP-ACI-3\"-C1F-259")
("3\"-D261623A764A9047E0E948EE25" "3940KP-ACI-3\"-C1F-260")
("2 1/2\"-3C17D32E8AAAB74571599AB915" "3940KP-ACI-2 1/2\"-C1F-261")
("3\"-3D89F89D17B84B433B5A67F8B9" "3940KP-ACI-3\"-C1F-262")
("2\"-ED5B31F38D403A4822C8463C00" "3940KP-ACI-2\"-C1F-263")
("2 1/2\"-F18AC699EF1D5A483DE9DE32C1" "3940KP-ACI-2 1/2\"-C1F-264")
("2\"-881470607C5C1E44E619658D24" "3940KP-ACI-2\"-C1F-265")
("2 1/2\"-58ED67139B8211402DF86EE411" "3940KP-ACI-2 1/2\"-C1F-266")
("3\"-91193845D697CB4391EB16B2D1" "3940KP-ACI-3\"-C1F-220")
("3\"-42BB6BD0C6999A4246F9389A7E" "3940KP-ACI-3\"-C1F-221")
("3\"-42C78E78CB6A224AD198916E6A" "3940KP-ACI-3\"-C1F-222")
("3\"-8D8FADFE27BDE248701AC352BA" "3940KP-ACI-3\"-C1F-223")
("3\"-A9B79B088DAA804922CAEB9D1B" "3940KP-ACI-3\"-C1F-224")
("3\"-B77F26E5E6BEBA49ED5B3537CC" "3940KP-ACI-3\"-C1F-225")
("3\"-346D816027A71F4FE1BAB5D9DE" "3940KP-ACI-3\"-C1F-226")
("3\"-0D5D731D41E36141C819BFAFBC" "3940KP-ACI-3\"-C1F-227")
("2 1/2\"-410D4391898CD2488BEA6A17CB" "3940KP-ACI-2 1/2\"-C1F-228")
("3\"-8244451E1AED34453AEA723923" "3940KP-ACI-3\"-C1F-229")
("2\"-7A152D5CC5E40149253A7E5CA9" "3940KP-ACI-2\"-C1F-230")
("2 1/2\"-C27D9C42BB6BD04C699AA246F3" "3940KP-ACI-2 1/2\"-C1F-231")
("2\"-389A7E42C78E784CB6A82AD190" "3940KP-ACI-2\"-C1F-232")
("2 1/2\"-916E6A8D8FADFE427BDB28701A" "3940KP-ACI-2 1/2\"-C1F-233")
("2 1/2\"-49AB9153D89F894D17BA4B33B5" "3940KP-ACI-2 1/2\"-C1F-234")
("2 1/2\"-A67F8B9ED5B31F438D483A822C" "3940KP-ACI-2 1/2\"-C1F-235")
("2 1/2\"-2463C00F18AC6949EF1B5A83DE" "3940KP-ACI-2 1/2\"-C1F-236")
("2 1/2\"-5DE32C18814706407C5A1E4E61" "3940KP-ACI-2 1/2\"-C1F-237")
("2 1/2\"-4658D2458ED671439B881102DF" "3940KP-ACI-2 1/2\"-C1F-238")
("2\"-26EE411E6F883E453F4922DD68" "3940KP-ACI-2\"-C1F-239")
("2 1/2\"-C5B5C2521F54B649B9D939AC4E" "3940KP-ACI-2 1/2\"-C1F-240")
("1 1/2\"-7C68D1D766572042B4F9564B4D" "3940KP-ACI-1 1/2\"-C1F-241")
("2\"-974A759C773E7D4261683A764A" "3940KP-ACI-2\"-C1F-242")
("1 1/2\"-907E0E348EE2534C17D92E8AAA" "3940KP-ACI-1 1/2\"-C1F-243")
("2\"-B7571549AB91534D89FA9D17B8" "3940KP-ACI-2\"-C1F-244")
("4\"-7571549AB9153D489F8AD17B84" "3940KP-ACI-4\"-C1F-286")
("4\"-B33B5A67F8B9ED45B31B38D403" "3940KP-ACI-4\"-C1F-287")
("3\"-A822C2463C00F148AC6A9EF1D5" "3940KP-ACI-3\"-C1F-288")
("4\"-A83DE5DE32C18841470907C5C1" "3940KP-ACI-4\"-C1F-289")
("4\"-E4E614658D24584ED67839B821" "3940KP-ACI-4\"-C1F-290")
("1\"-102DF26EE411E64F883B53F472" "3940KP-ACI-1\"-C1F-291")
("3\"-2DD68C5B5C25214F54B99B9D33" "3940KP-ACI-3\"-C1F-292")
("1\"-9AC4E7C68D1D764657282B4F45" "3940KP-ACI-1\"-C1F-293")
("3\"-64B4D974A759C7473E7B261623" "3940KP-ACI-3\"-C1F-294")
("1\"-A764A907E0E3484EE259C17D32" "3940KP-ACI-1\"-C1F-295")
("3\"-E8AAAB7571549A4B9159D89F89" "3940KP-ACI-3\"-C1F-296")
("1\"-D17B84B33B5A674F8B9BD5B31F" "3940KP-ACI-1\"-C1F-297")
("3\"-38D403A822C24643C00B18AC69" "3940KP-ACI-3\"-C1F-298")
("3\"-9EF1D5A83DE5DE432C1A814706" "3940KP-ACI-3\"-C1F-299")
("3\"-07C5C1E4E6146548D2498ED671" "3940KP-ACI-3\"-C1F-300")
("2 1/2\"-39B821102DF26E4E411B6F883E" "3940KP-ACI-2 1/2\"-C1F-301")
("2\"-53F4722DD68C5B45C2581F54B6" "3940KP-ACI-2\"-C1F-302")
("3\"-9B9D339AC4E7C648D1D9665720" "3940KP-ACI-3\"-C1F-303")
("2 1/2\"-2B4F4564B4D9744A759A773E7D" "3940KP-ACI-2 1/2\"-C1F-304")
("3\"-B391ED16A2D1864F090841ADDD" "3940KP-ACI-3\"-C1F-267")
("3\"-E68A377CDEB38641BB2AC1FAE6" "3940KP-ACI-3\"-C1F-268")
("3\"-6E25D4D5A3ADC24C4E2936B023" "3940KP-ACI-3\"-C1F-269")
("3\"-5CB45E17960EED4FACE9CC1DEC" "3940KP-ACI-3\"-C1F-270")
("3\"-4C660C30D25FFB4B46A993AF3F" "3940KP-ACI-3\"-C1F-271")
("3\"-EC3284787B11774A2C5A46BEB5" "3940KP-ACI-3\"-C1F-272")
("3\"-34340D092D2342492B69285269" "3940KP-ACI-3\"-C1F-273")
("2 1/2\"-E6F883E53F47224DD68A5B5C25" "3940KP-ACI-2 1/2\"-C1F-274")
("2\"-21F54B69B9D3394AC4E9C68D1D" "3940KP-ACI-2\"-C1F-275")
("3\"-76657202B4F45644B4DA74A759" "3940KP-ACI-3\"-C1F-276")
("2 1/2\"-C773E7D261623A4764AA07E0E3" "3940KP-ACI-2 1/2\"-C1F-277")
("2 1/2\"-48EE253C17D32E48AAAA757154" "3940KP-ACI-2 1/2\"-C1F-278")
("2 1/2\"-9AB9153D89F89D417B89B33B5A" "3940KP-ACI-2 1/2\"-C1F-279")
("2 1/2\"-67F8B9ED5B31F348D409A822C2" "3940KP-ACI-2 1/2\"-C1F-280")
("2 1/2\"-463C00F18AC6994EF1D9A83DE5" "3940KP-ACI-2 1/2\"-C1F-281")
("2\"-DE32C18814706047C5C8E4E614" "3940KP-ACI-2\"-C1F-282")
("1 1/2\"-658D2458ED671349B828102DF2" "3940KP-ACI-1 1/2\"-C1F-283")
("2 1/2\"-6EE411E6F883E543F4782DD68C" "3940KP-ACI-2 1/2\"-C1F-284")
("2\"-5B5C2521F54B694B9D399AC4E7" "3940KP-ACI-2\"-C1F-285")
("4\"-7F8B9ED5B31F384D403A822C24" "3940KP-ACI-4\"-C1F-319")
("3\"-63C00F18AC699E4F1D5A83DE5D" "3940KP-ACI-3\"-C1F-320")
("1\"-E32C18814706074C5C1B4E6146" "3940KP-ACI-1\"-C1F-321")
("4\"-58D2458ED671394B821802DF26" "3940KP-ACI-4\"-C1F-322")
("4\"-EE411E6F883E534F4728DD68C5" "3940KP-ACI-4\"-C1F-323")
("3\"-B5C2521F54B69B49D33AAC4E7C" "3940KP-ACI-3\"-C1F-324")
("1\"-68D1D76657202B44F4594B4D97" "3940KP-ACI-1\"-C1F-325")
("3\"-4A759C773E7D2641623A764A90" "3940KP-ACI-3\"-C1F-326")
("1\"-7E0E348EE253C147D32B8AAAB7" "3940KP-ACI-1\"-C1F-327")
("3\"-571549AB9153D849F89B17B84B" "3940KP-ACI-3\"-C1F-328")
("1\"-33B5A67F8B9ED54B31F98D403A" "3940KP-ACI-1\"-C1F-329")
("3\"-822C2463C00F184AC69AEF1D5A" "3940KP-ACI-3\"-C1F-330")
("3\"-83DE5DE32C18814470687C5C1E" "3940KP-ACI-3\"-C1F-331")
("3\"-4E614658D2458E4D67199B8211" "3940KP-ACI-3\"-C1F-332")
("3\"-02DF26EE411E6F4883E93F4722" "3940KP-ACI-3\"-C1F-333")
("4\"-00C807AF9EAB404FD32A0798BC" "3940KP-ACI-4\"-C1F-305")
("3\"-188BEC6A16CA71444458E1ADD3" "3940KP-ACI-3\"-C1F-306")
("3\"-4529EC7238237A4151C9CB4E4F" "3940KP-ACI-3\"-C1F-307")
("3\"-1914387E5CA9C246C9C92AB5BD" "3940KP-ACI-3\"-C1F-308")
("3\"-261623A764A9074E0E398EE253" "3940KP-ACI-3\"-C1F-309")
("3\"-C17D32E8AAAB7547154AAB9153" "3940KP-ACI-3\"-C1F-310")
("3\"-D89F89D17B84B343B5A97F8B9E" "3940KP-ACI-3\"-C1F-311")
("3\"-D5B31F38D403A8422C2963C00F" "3940KP-ACI-3\"-C1F-312")
("3\"-18AC699EF1D5A843DE5BE32C18" "3940KP-ACI-3\"-C1F-313")
("2 1/2\"-81470607C5C1E44E614958D245" "3940KP-ACI-2 1/2\"-C1F-314")
("2 1/2\"-8ED67139B8211042DF29EE411E" "3940KP-ACI-2 1/2\"-C1F-315")
("2 1/2\"-6F883E53F4722D4D68C9B5C252" "3940KP-ACI-2 1/2\"-C1F-316")
("2 1/2\"-1F54B69B9D339A4C4E7A68D1D7" "3940KP-ACI-2 1/2\"-C1F-317")
("4\"-AB9153D89F89D147B84A33B5A6" "3940KP-ACI-4\"-C1F-318")
("4\"-8AAAB7571549AB49153B89F89D" "3940KP-ACI-4\"-C1F-342")
("4\"-17B84B33B5A67F48B9EB5B31F3" "3940KP-ACI-4\"-C1F-343")
("4\"-8D403A822C24634C00F88AC699" "3940KP-ACI-4\"-C1F-344")
("4\"-EF1D5A83DE5DE342C18A147060" "3940KP-ACI-4\"-C1F-345")
("4\"-7C5C1E4E6146584D245AED6713" "3940KP-ACI-4\"-C1F-346")
("3\"-3F4722DD68C5B54C2528F54B69" "3940KP-ACI-3\"-C1F-347")
("3\"-B9D339AC4E7C684D1D79657202" "3940KP-ACI-3\"-C1F-348")
("3\"-B4F4564B4D974A4759C973E7D2" "3940KP-ACI-3\"-C1F-349")
("3\"-61623A764A907E40E34AEE253C" "3940KP-ACI-3\"-C1F-350")
("3\"-EB58889135D2274896D91B66C6" "3940KP-ACI-3\"-C1F-334")
("3\"-BFE9D55D14C3C44929CA1B3D13" "3940KP-ACI-3\"-C1F-335")
("3\"-25AE124BA34D06485EDBCE9BD3" "3940KP-ACI-3\"-C1F-336")
("3\"-BB0CDB3B55EB2E4C14EBAA3592" "3940KP-ACI-3\"-C1F-337")
("2 1/2\"-DD68C5B5C2521F454B6AB9D339" "3940KP-ACI-2 1/2\"-C1F-338")
("2 1/2\"-AC4E7C68D1D766457208B4F456" "3940KP-ACI-2 1/2\"-C1F-339")
("2 1/2\"-4B4D974A759C7743E7D861623A" "3940KP-ACI-2 1/2\"-C1F-340")
("2 1/2\"-764A907E0E348E4E253A17D32E" "3940KP-ACI-2 1/2\"-C1F-341")
("8\"-17D32E8AAAB75741549AB9153D" "3000KP-ACI-8\"-C1F-1825")
("1\"-F8B9ED5B31F38D4403AA22C246" "3000KP-ACI-1\"-C1F-1826")
("3\"-3C00F18AC699EF41D5AA3DE5DE" "3000KP-ACI-3\"-C1F-1827")
("4\"-32C1881470607C45C1E9E61465" "3000KP-ACI-4\"-C1F-1828")
("3\"-8D2458ED67139B4821182DF26E" "3000KP-ACI-3\"-C1F-1829")
("2 1/2\"-E411E6F883E53F44722BD68C5B" "3000KP-ACI-2 1/2\"-C1F-1830")
("1\"-5C2521F54B69B94D339AC4E7C6" "3000KP-ACI-1\"-C1F-1831")
("3\"-B0D934A359837E4E79D9C6D3A3" "3000KP-ACI-3\"-C1F-1832")
("3\"-317284787B05774A209A46BEB5" "3000KP-ACI-3\"-C1F-1833")
("2 1/2\"-33340249216342492BA9285269" "3000KP-ACI-2 1/2\"-C1F-1834")
("1\"-CB88137F6F6C0C4B9EE904548C" "3000KP-ACI-1\"-C1F-1835")
("3\"-8D1D76657202B44F4569B4D974" "3000KP-ACI-3\"-C1F-1836")
("3\"-EDA1DAE2CC95C448C6B981CCA0" "3000KP-ACI-3\"-C1F-1837")
("4\"-3A18A9CD299CFD47B27BB82555" "3000KP-ACI-4\"-C1F-1838")
("3\"-62F2BEE4563AFD48349948B262" "3000KP-ACI-3\"-C1F-1839")
("2 1/2\"-D6DC50512A254948F6DAAD37DA" "3000KP-ACI-2 1/2\"-C1F-1840")
("3\"-D43BC6CE1D7AA94B3578449AA8" "3000KP-ACI-3\"-C1F-1841")
("3\"-89F89D17B84B334B5A69F8B9ED" "3000KP-ACI-3\"-C1F-1842")
("2 1/2\"-5B31F38D403A8242C2493C00F1" "3000KP-ACI-2 1/2\"-C1F-1843")
("3\"-8AC699EF1D5A834DE5DB32C188" "3000KP-ACI-3\"-C1F-1844")
("3\"-1470607C5C1E4E4614698D2458" "3000KP-ACI-3\"-C1F-1845")
("4\"-ED67139B8211024DF26BE411E6" "3000KP-ACI-4\"-C1F-1846")
("3\"-F883E53F4722DD468C5A5C2521" "3000KP-ACI-3\"-C1F-1847")
("2 1/2\"-F54B69B9D339AC44E7C98D1D76" "3000KP-ACI-2 1/2\"-C1F-1848")
("3\"-657202B4F4564B44D979A759C7" "3000KP-ACI-3\"-C1F-1849")
("3\"-73E7D261623A7644A909E0E348" "3000KP-ACI-3\"-C1F-1850")
("2 1/2\"-EE253C17D32E8A4AAB7971549A" "3000KP-ACI-2 1/2\"-C1F-1851")
("3\"-B9153D89F89D174B84B93B5A67" "3000KP-ACI-3\"-C1F-1852")
("4\"-A759C773E7D2614623A964A907" "3000KP-ACI-4\"-C1F-1853")
("1\"-E0E348EE253C174D32EAAAAB75" "3000KP-ACI-1\"-C1F-1854")
("2\"-3DE5DE32C18814470609C5C1E4" "3000KP-ACI-2\"-C1F-1855")
("3\"-C4E7C68D1D766547202A4F4564" "3000KP-ACI-3\"-C1F-1856")
("1\"-B4D974A759C7734E7D291623A7" "3000KP-ACI-1\"-C1F-1857")
("3\"-7BE585190F838445C589CB291D" "3000KP-ACI-3\"-C1F-1858")
("1\"-71549AB9153D894F89D87B84B3" "3000KP-ACI-1\"-C1F-1859")
("2\"-3B5A67F8B9ED5B431F3AD403A8" "3000KP-ACI-2\"-C1F-1860")
("3\"-22C2463C00F18A4C699BF1D5A8" "3000KP-ACI-3\"-C1F-1861")
("1\"-E614658D2458ED46713AB82110" "3000KP-ACI-1\"-C1F-1862")
("2\"-2DF26EE411E6F8483E59F4722D" "3000KP-ACI-2\"-C1F-1863")
("3\"-D68C5B5C2521F544B69A9D339A" "3000KP-ACI-3\"-C1F-1864")
("4\"-64A907E0E348EE4253C87D32E8" "3000KP-ACI-4\"-C1F-1865")
("3\"-F4722DD68C5B5C42521B54B69B" "3000KP-ACI-3\"-C1F-1866")
("3\"-AC699EF1D5A83D4E5DE92C1881" "3000KP-ACI-3\"-C1F-1867")
("3\"-A95B86AD88408E4372794B875B" "3000KP-ACI-3\"-C1F-1868")
("3\"-A28021459114754D38E9309CCC" "3000KP-ACI-3\"-C1F-1869")
("3\"-FA8A488CDEC48642BC3AC24BEB" "3000KP-ACI-3\"-C1F-1870")
("3\"-81871A0BC5C1E443A18958D295" "3000KP-ACI-3\"-C1F-1871")
("3\"-D54CD7DE2E8BBA4C3578559AB9" "3000KP-ACI-3\"-C1F-1872")
("3\"-7B94EF6E043D294A2588718D6D" "3000KP-ACI-3\"-C1F-1873")
("3\"-76B6D8BDBF59BC4E65DB8A03F9" "3000KP-ACI-3\"-C1F-1874")
("3\"-DEDEACE4CB1DEC44C658C30C14" "3000KP-ACI-3\"-C1F-1875")
("3\"-55119C08E8059545387B9CED16" "3000KP-ACI-3\"-C1F-1876")
("3\"-C346D816027A714EFE1A9B5D9D" "3000KP-ACI-3\"-C1F-1877")
("3\"-563A4D874A748B4662D9D15051" "3000KP-ACI-3\"-C1F-1878")
("3\"-80CB9FE5C464894D457A927C38" "3000KP-ACI-3\"-C1F-1879")
("3\"-C936667313C0054674B8E944A4" "3000KP-ACI-3\"-C1F-1880")
("3\"-BF39D95D44C7C84919CA1F6D52" "3000KP-ACI-3\"-C1F-1881")
("3\"-7A04B7A209949B4DA47978F24D" "3000KP-ACI-3\"-C1F-1882")
("3\"-77BCDB3751AB2A4C1FAB66E15D" "3000KP-ACI-3\"-C1F-1883")
("3\"-93A0804272947948B15A8B31AA" "3000KP-ACI-3\"-C1F-1884")
("3\"-45BDA43334F249411639182BA5" "3000KP-ACI-3\"-C1F-1885")
("3\"-7DA8CFAA66E15D44D5ABA97DC3" "3000KP-ACI-3\"-C1F-1886")
("3\"-03547CD447E8264128A9100F1C" "3000KP-ACI-3\"-C1F-1887")
("3\"-03B4F4664B5D9844A75AC773E7" "3000KP-ACI-3\"-C1F-1888")
("3\"-47B6B781CCA0E64C465A9D558B" "3000KP-ACI-3\"-C1F-1889")
("3\"-B49E5A96F2323E4CE8CA12318C" "3000KP-ACI-3\"-C1F-1890")
("3\"-C7238237A151C54CB4E9F19143" "3000KP-ACI-3\"-C1F-1891")
("3\"-ED4B30E38C3E294812B8363CEF" "3000KP-ACI-3\"-C1F-1892")
("1\"-56DF2BEE4563AF4D834A348726" "3000KP-ACI-1\"-C1F-1893")
("3\"-470607C5C1E4E641465AD2458E" "3000KP-ACI-3\"-C1F-1894")
("3\"-AAAB7571549AB94153DA9F89D1" "3000KP-ACI-3\"-C1F-1895")
("3\"-7B84B33B5A67F84B9ED9B31F38" "3000KP-ACI-3\"-C1F-1896")
("3\"-D403A822C2463C400F1AAC699E" "3000KP-ACI-3\"-C1F-1897")
("3\"-F1D5A83DE5DE324C1888470607" "3000KP-ACI-3\"-C1F-1898")
("3\"-C5C1E4E614658D42458BD67139" "3000KP-ACI-3\"-C1F-1899")
("3\"-B821102DF26EE4411E6B883E53" "3000KP-ACI-3\"-C1F-1900")
("3\"-9D339AC4E7C68D41D76957202B" "3000KP-ACI-3\"-C1F-1901")
("3\"-4F4564B4D974A7459C793E7D26" "3000KP-ACI-3\"-C1F-1902")
("3\"-1623A764A907E04E348BE253C1" "3000KP-ACI-3\"-C1F-1903")
("3\"-7D32E8AAAB75714549AA9153D8" "3000KP-ACI-3\"-C1F-1904")
("3\"-9F89D17B84B33B45A67B8B9ED5" "3000KP-ACI-3\"-C1F-1905")
("3\"-B31F38D403A8224C2469C00F18" "3000KP-ACI-3\"-C1F-1906")
("8\"-883E53F4722DD648C5B9C2521F" "3000KP-ACI-8\"-C1F-1907")
("6\"-D67139B821102D4F26EB411E6F" "3000KP-ACI-6\"-C1F-1908")
("4\"-E253C17D32E8AA4AB319C10567" "3000KP-ACI-4\"-C1F-1909")
("3\"-D8C44CF3B2B38148CA0A2C0214" "3000KP-ACI-3\"-C1F-1910")
("1\"-FCCA2B54EA1EBF43DD9A248171" "3000KP-ACI-1\"-C1F-1911")
("2\"-8D1DCB1F7257694EE56A0A3824" "3000KP-ACI-2\"-C1F-1912")
("2\"-75285269441C5B4F4D3B185427" "3000KP-ACI-2\"-C1F-1913")
("2\"-F6C46589E558B9437D4A74E111" "3000KP-ACI-2\"-C1F-1914")
("4\"-7313C005674B1E4945B959C373" "3000KP-ACI-4\"-C1F-1915")
("4\"-7F66E9EAB3BEC3428F7937C174" "3000KP-ACI-4\"-C1F-1916")
("4\"-B32AB5BCFC68984A135B337897" "3000KP-ACI-4\"-C1F-1917")
("4\"-7B95EF6E043D2A4A3598718E6E" "3000KP-ACI-4\"-C1F-1918")
("4\"-206173676AF467491F8A35ADA4" "3000KP-ACI-4\"-C1F-1919")
("4\"-7778468D65A7864D60EA6C96AD" "3000KP-ACI-4\"-C1F-1920")
("3\"-5C1E945B459C3744F7EB71623B" "3000KP-ACI-3\"-C1F-1921")
("2\"-475A917ECBE49F4BE64BD8D02E" "3000KP-ACI-2\"-C1F-1922")
("2\"-8BBBC468255ABC49264B9A19AE" "3000KP-ACI-2\"-C1F-1923")
("2\"-9D114A923CE5744DCCBB9BD2AA" "3000KP-ACI-2\"-C1F-1924")
("3\"-BA6CA7BE9951914483895D987C" "3000KP-ACI-3\"-C1F-1925")
("2\"-4B29BADE3AAD1E48C28BC93666" "3000KP-ACI-2\"-C1F-1926")
("2\"-EA8A377CDDB38641BB2AC14AEA" "3000KP-ACI-2\"-C1F-1927")
("2\"-4C43B6B7818CA04E6C48149D41" "3000KP-ACI-2\"-C1F-1928")
("4\"-AC932213DBD7FB4012F9095306" "3000KP-ACI-4\"-C1F-1929")
("3\"-71623B475A917E4CBE4AFBE64D" "3000KP-ACI-3\"-C1F-1930")
("1\"-9A19AED8C44CF34B2B3A18CA0A" "3000KP-ACI-1\"-C1F-1931")
("2\"-2C02149D114A9243CE594DCCBD" "3000KP-ACI-2\"-C1F-1932")
("2\"-8855CF3C2B38C8486BA8C02149" "3000KP-ACI-2\"-C1F-1933")
("2\"-9F03A4D2CD463C4BBBCA68295A" "3000KP-ACI-2\"-C1F-1934")
("3\"-315833EA39D2C24DE638065B3A" "3000KP-ACI-3\"-C1F-1935")
("2\"-BAEF4AAD1E8C394EDA49667313" "3000KP-ACI-2\"-C1F-1936")
("2\"-C105675C1E945B4459C974F7EE" "3000KP-ACI-2\"-C1F-1937")
("2\"-D8D02E8BBBC4684255AAC9264E" "3000KP-ACI-2\"-C1F-1938")
("3\"-48EF254C27D32E48ABAA757155" "3000KP-ACI-3\"-C1F-1939")
("2\"-DEFC5972CD4CD245B0B9076E9E" "3000KP-ACI-2\"-C1F-1940")
("2\"-EF703276D4B98B415B8A219A4A" "3000KP-ACI-2\"-C1F-1941")
("2\"-474D00F18AC6A94E01E9A83DE5" "3000KP-ACI-2\"-C1F-1942")
("4\"-9BD2AAFCCA2B544EA1EAF3DD99" "3000KP-ACI-4\"-C1F-1943")
("2\"-667313C105675C41E949B459C3" "3000KP-ACI-2\"-C1F-1944")
("3\"-FBE64DD8D02E8B4BBC498255AB" "3000KP-ACI-3\"-C1F-1945")
("1\"-C9264E9A19AED84C44CB3B2B38" "3000KP-ACI-1\"-C1F-1946")
("2\"-01E6E842E52F47422D988C1B1C" "3000KP-ACI-2\"-C1F-1947")
("2\"-5C986CB29121564A12496E49F5" "3000KP-ACI-2\"-C1F-1948")
("2\"-EB57879424D2264786D80B56C5" "3000KP-ACI-2\"-C1F-1949")
("2\"-2481718D1DCB1F4725799EE568" "3000KP-ACI-2\"-C1F-1950")
("3\"-0A3824AC9322134DBD7BB012F7" "3000KP-ACI-3\"-C1F-1951")
("2\"-095306315833EA439D2A2DE632" "3000KP-ACI-2\"-C1F-1952")
("2\"-065B3ABAEF4AAD41E8C99EDA46" "3000KP-ACI-2\"-C1F-1953")
("2\"-74F7EE71623B4745A919ECBE49" "3000KP-ACI-2\"-C1F-1954")
("2\"-33EE7AD6C6D37342165A7ACBE4" "3000KP-ACI-2\"-C1F-1955")
("3\"-B225C6F4E1685F4DDDEA8A4C7C" "3000KP-ACI-3\"-C1F-1956")
("2\"-563A4D8739748B4662D9D15F51" "3000KP-ACI-2\"-C1F-1957")
("2\"-E732165C3ACBEF44ABD8F8D39F" "3000KP-ACI-2\"-C1F-1958")
("2\"-85E2213DBE7BB0422F7A95F06E" "3000KP-ACI-2\"-C1F-1959")
("4\"-F3DD992481718D41DCB8F72576" "3000KP-ACI-4\"-C1F-1960")
("2\"-B012F70953063145833BA39D2C" "3000KP-ACI-2\"-C1F-1961")
("4\"-B459C374F7EE714623B975A917" "3000KP-ACI-4\"-C1F-1962")
("3\"-ECBE49FBE64DD84D02EABBBC46" "3000KP-ACI-3\"-C1F-1963")
("1\"-37A141C5BB4E4E41814877D5C9" "3000KP-ACI-1\"-C1F-1964")
("1\"-8C16C8B31AA5BC4FC68A89135E" "3000KP-ACI-1\"-C1F-1965")
("3\"-216786D2FA56C546A94A118BF8" "3000KP-ACI-3\"-C1F-1966")
("1\"-C6D4B475A6C7AC4BE49ABE64DD" "3000KP-ACI-1\"-C1F-1967")
("1\"-E1695FDDDEACE44CB1DBB4C650" "3000KP-ACI-1\"-C1F-1968")
("2\"-18CA0A2C02149D4114AA23CE57" "3000KP-ACI-2\"-C1F-1969")
("3\"-4DCCBD9BD2AAFC4CA2B94EA1EB" "3000KP-ACI-3\"-C1F-1970")
("1\"-9EE5680A3824AC4932283DBD7F" "3000KP-ACI-1\"-C1F-1971")
("3\"-2DE632065B3ABA4EF4AAD1E8C3" "3000KP-ACI-3\"-C1F-1972")
("1\"-9EDA46667313C1405679C1E945" "3000KP-ACI-1\"-C1F-1973")
("2\"-CF75EE9B13098848957AE66B89" "3000KP-ACI-2\"-C1F-1974")
("3\"-D6E872E52E36114CC58A4A4B15" "3000KP-ACI-3\"-C1F-1975")
("1\"-876BA2C0214990414A5B3CE574" "3000KP-ACI-1\"-C1F-1976")
("3\"-98879535D6278846D70AA6C97B" "3000KP-ACI-3\"-C1F-1977")
("1\"-833FB3AE3C2DE7443169C3ACBE" "3000KP-ACI-1\"-C1F-1978")
("8\"-3B2B3818CA0A2C40214AD114A9" "3000KP-ACI-8\"-C1F-1979")
("1\"-4EA1EBF3DD992448171AD1DCB1" "3000KP-ACI-1\"-C1F-1980")
("3\"-3DBD7FB012F70945306915833E" "3000KP-ACI-3\"-C1F-1981")
("1\"-D1E8C39EDA466647313A105675" "3000KP-ACI-1\"-C1F-1982")
("2\"-75A917ECBE49FB4E64DB8D02E8" "3000KP-ACI-2\"-C1F-1983")
("1 1/2\"-BBBC468255ABC94264EAA19AED" "3000KP-ACI-1 1/2\"-C1F-1984")
("4\"-8A135E337897E341C67B68CB6A" "3000KP-ACI-4\"-C1F-1985")
("4\"-119C09E805D5974C7E9AED16AD" "3000KP-ACI-4\"-C1F-1986")
("3\"-23CE574DCCBD9B4D2AABCCA2B5" "3000KP-ACI-3\"-C1F-1987")
("2\"-F725769EE5680A43824AC93221" "3000KP-ACI-2\"-C1F-1988")
("1 1/2\"-A39D2C2DE6320645B3AAAEF4AA" "3000KP-ACI-1 1/2\"-C1F-1989")
("1\"-C1E945B459C3744F7EE91623B4" "3000KP-ACI-1\"-C1F-1990")
("3\"-7BF9FAC41FD33940898AC288BE" "3000KP-ACI-3\"-C1F-1991")
("2\"-19E4A0EB578784424D286786D2" "3000KP-ACI-2\"-C1F-1992")
("1 1/2\"-61BC3BC14AEA6E465E8B9A3AEC" "3000KP-ACI-1 1/2\"-C1F-1993")
("1\"-88E5CA9C27D9C442BB6AD0C799" "3000KP-ACI-1\"-C1F-1994")
("4\"-8C44CF3B2B38184CA0A8C02149" "3000KP-ACI-4\"-C1F-1995")
("3\"-105675C1E945B4459C394F7EE7" "3000KP-ACI-3\"-C1F-1996")
("3\"-A3824AC932213D4BD7FA012F70" "3000KP-ACI-3\"-C1F-1997")
("4\"-95306315833EA349D2C8DE6320" "3000KP-ACI-4\"-C1F-1998")
("4\"-A1EBF3DD9924814718D8DCB1F7" "3000KP-ACI-4\"-C1F-1999")
("4\"-7ACAE44ABD5F8D479E2B867683" "3000KP-ACI-4\"-C1F-2000")
("4\"-9B5D9DE0D5D7314D41D9510C81" "3000KP-ACI-4\"-C1F-2001")
("4\"-C6A17CB72444514E1AEB3452AE" "3000KP-ACI-4\"-C1F-2002")
("4\"-D834A348B262D64DC60912A264" "3000KP-ACI-4\"-C1F-2003")
("4\"-98F6DBAD37EAD543CC6AE1D7AA" "3000KP-ACI-4\"-C1F-2004")
("4\"-AC468155ABB91644E9989AED8C" "3000KP-ACI-4\"-C1F-2005")
("4\"-55D04C3C4919CB41B3D8325AE1" "3000KP-ACI-4\"-C1F-2006")
("4\"-E18701AC252BAA49B68A088C9A" "3000KP-ACI-4\"-C1F-2007")
("4\"-8F822B8EB9D1BA477F29E5E6BE" "3000KP-ACI-4\"-C1F-2008")
("4\"-CB9EE504548CD4447E886138A7" "3000KP-ACI-4\"-C1F-2009")
("4\"-200F1CAC6E9E014D6E892E52E3" "3000KP-ACI-4\"-C1F-2010")
("4\"-B662D6D150512A46649AF6DFE2" "3000KP-ACI-4\"-C1F-2011")
("4\"-7B3369715A17524BEEEBB9B488" "3000KP-ACI-4\"-C1F-2012")
("4\"-DEEC4972CC3CD245BFB9066E9E" "3000KP-ACI-4\"-C1F-2013")
("4\"-BC4C0D439186484D2859ED6717" "3000KP-ACI-4\"-C1F-2014")
("4\"-8B825546CE1AEE43453AEC8239" "3000KP-ACI-4\"-C1F-2015")
("3\"-348736EE79D6C64C3A39495B6A" "3000KP-ACI-3\"-C1F-2016")
("3\"-BAE38AAD53CC794E2D89667357" "3000KP-ACI-3\"-C1F-2017")
("3\"-D55A785D6FE96C496ADA844CF3" "3000KP-ACI-3\"-C1F-2018")
("3\"-8E805955387E9C4ED169DD182B" "3000KP-ACI-3\"-C1F-2019")
("1\"-09B241A999A6464E738A97E82C" "3000KP-ACI-1\"-C1F-2020")
("3\"-D114A923CE574D4CCBDABD2AAF" "3000KP-ACI-3\"-C1F-2021")
("3\"-CCA2B54EA1EBF34DD998481718" "3000KP-ACI-3\"-C1F-2022")
("3\"-D1DCB1F725769E4E5688A3824A" "3000KP-ACI-3\"-C1F-2023")
("3\"-C932213DBD7FB0412F78953063" "3000KP-ACI-3\"-C1F-2024")
("3\"-15833EA39D2C2D4E632865B3AB" "3000KP-ACI-3\"-C1F-2025")
("3\"-AEF4AAD1E8C39E4DA46967313C" "3000KP-ACI-3\"-C1F-2026")
("3\"-1623B475A917EC4BE49BBE64DD" "3000KP-ACI-3\"-C1F-2027")
("3\"-8D02E8BBBC4682455ABA9264E9" "3000KP-ACI-3\"-C1F-2028")
("3\"-A19AED8C44CF3B42B3888CA0A2" "3000KP-ACI-3\"-C1F-2029")
("3\"-C02149D114A9234CE579DCCBD9" "3000KP-ACI-3\"-C1F-2030")
("3\"-BD2AAFCCA2B54E4A1EBB3DD992" "3000KP-ACI-3\"-C1F-2031")
("3\"-481718D1DCB1F742576AEE5680" "3000KP-ACI-3\"-C1F-2032")
("4\"-DCCBD9BD2AAFCC4A2B59EA1EBF" "3000KP-ACI-4\"-C1F-2033")
("3\"-CBE49FBE64DD8D402E8ABBC468" "3000KP-ACI-3\"-C1F-2034")
("3\"-255ABC9264E9A149AEDAC44CF3" "3000KP-ACI-3\"-C1F-2035")
("3\"-1C31D25FFB707A4E9EAA40ED32" "3000KP-ACI-3\"-C1F-2036")
("3\"-A18A9CD289BED64B17DA825546" "3000KP-ACI-3\"-C1F-2037")
("4\"-202BFF4564B0D9434A399C363E" "3000KP-ACI-4\"-C1F-2038")
("4\"-4AA3C3DF7F31664C3B89B05B7A" "3000KP-ACI-4\"-C1F-2039")
("4\"-EC66178A7244454CE1ABD3452A" "3000KP-ACI-4\"-C1F-2040")
("4\"-EC7239237615CC458B5A4B1915" "3000KP-ACI-4\"-C1F-2041")
("4\"-494B69BAD37AAD453BC98E1D76" "3000KP-ACI-4\"-C1F-2042")
("4\"-324F248116331842AA58742694" "3000KP-ACI-4\"-C1F-2043")
("4\"-4008AE7D7E47434276DABDBF55" "3000KP-ACI-4\"-C1F-2044")
("4\"-CD072AF9B141A8498A595E7378" "3000KP-ACI-4\"-C1F-2045")
("4\"-A8F82DB8EB8C0A4A73B86A4957" "3000KP-ACI-4\"-C1F-2046")
("4\"-EBA8DD4A34367C43369915B275" "3000KP-ACI-4\"-C1F-2047")
("4\"-3D00F1CAC699EF41D6AA3DE5DE" "3000KP-ACI-4\"-C1F-2048")
("4\"-039D95D54C7C89429DB807D532" "3000KP-ACI-4\"-C1F-2049")
("4\"-5AE625CA34D46845E2283ACE7B" "3000KP-ACI-4\"-C1F-2050")
("4\"-C23318DA611702465F4AB46A39" "3000KP-ACI-4\"-C1F-2051")
("4\"-4B1814283958A84C268AB32AB5" "3000KP-ACI-4\"-C1F-2052")
("4\"-7CFC64546135A3437459A3CC63" "3000KP-ACI-4\"-C1F-2053")
("4\"-6304722EE79D6B45C3692055B6" "3000KP-ACI-4\"-C1F-2054")
("3\"-ACBE45BBE609D84A02EA777842" "3000KP-ACI-3\"-C1F-2055")
("3\"-4D516785D6FA964C96AB88408F" "3000KP-ACI-3\"-C1F-2056")
("3\"-65B3ABAEF4AAD14E8C3AEDA466" "3000KP-ACI-3\"-C1F-2057")
("3\"-67313C105675C14E945A459C37" "3000KP-ACI-3\"-C1F-2058")
("3\"-4F7EE71623B4754A917BCBE49F" "3000KP-ACI-3\"-C1F-2059")
("3\"-BE64DD8D02E8BB4BC46A255ABC" "3000KP-ACI-3\"-C1F-2060")
("3\"-9264E9A19AED8C444CF9B2B381" "3000KP-ACI-3\"-C1F-2061")
("3\"-8CA0A2C02149D1414A983CE574" "3000KP-ACI-3\"-C1F-2062")
("3\"-3DD992481718D14DCB1B725769" "3000KP-ACI-3\"-C1F-2063")
("3\"-EE5680A3824AC9432219DBD7FB" "3000KP-ACI-3\"-C1F-2064")
("3\"-012F70953063154833EA39D2C2" "3000KP-ACI-3\"-C1F-2065")
("3\"-DE632065B3ABAE4F4AAB1E8C39" "3000KP-ACI-3\"-C1F-2066")
("3\"-EDA46667313C1045675A1E945B" "3000KP-ACI-3\"-C1F-2067")
("3\"-459C374F7EE716423B495A917E" "3000KP-ACI-3\"-C1F-2068")
("4\"-B2B3818CA0A2C042149B114A92" "3000KP-ACI-4\"-C1F-2069")
("3\"-39D2C2DE6320654B3ABAEF4AAD" "3000KP-ACI-3\"-C1F-2070")
("3\"-C44CF3B2B3818C4A0A2A02149D" "3000KP-ACI-3\"-C1F-2071")
("3\"-114A923CE574DC4CBD9AD2AAFC" "3000KP-ACI-3\"-C1F-2072")
("3\"-CA2B54EA1EBF3D4D992981718D" "3000KP-ACI-3\"-C1F-2073")
("1\"-E3D3E0844276D44BDC085CCF21" "3000KP-ACI-1\"-C1F-2074")
("4\"-7C28EC9366572043B0F9664B1D" "3000KP-ACI-4\"-C1F-2075")
("3\"-3CE574DCCBD9BD42AAFACA2B54" "3000KP-ACI-3\"-C1F-2076")
("3\"-EA1EBF3DD9924841718B1DCB1F" "3000KP-ACI-3\"-C1F-2077")
("3\"-725769EE5680A34824AA932213" "3000KP-ACI-3\"-C1F-2078")
("3\"-DBD7FB012F70954306385833EA" "3000KP-ACI-3\"-C1F-2079")
("3\"-1E8C39EDA466674313C805675C" "3000KP-ACI-3\"-C1F-2080")
("3\"-1E945B459C374F47EE78623B47" "3000KP-ACI-3\"-C1F-2081")
("3\"-5A917ECBE49FBE464DDAD02E8B" "3000KP-ACI-3\"-C1F-2082")
("3\"-BBC468255ABC92464E9A19AED8" "3000KP-ACI-3\"-C1F-2083")
("4\"-05675C1E945B4549C379F7EE71" "3000KP-ACI-4\"-C1F-2084")
("3\"-D02E8BBBC4682545ABCA264E9A" "3000KP-ACI-3\"-C1F-2085")
("4\"-D2AAFCCA2B54EA41EBF9DD9924" "3000KP-ACI-4\"-C1F-2086")
("4\"-61271269040B4B4A3D3B080327" "3000KP-ACI-4\"-C1F-2087")
("4\"-8F6DBAD37DAC434BC6CB1D7AA9" "3000KP-ACI-4\"-C1F-2088")
("4\"-D468266ABCA2644F9A1AAED9C5" "3000KP-ACI-4\"-C1F-2089")
("4\"-2AC19E806D697C48E9DBD16BDD" "3000KP-ACI-4\"-C1F-2090")
("4\"-7EC66128A7100F41CE19DD3F1D" "3000KP-ACI-4\"-C1F-2091")
("4\"-E821B8DB8CFAA646E25B4D5AEA" "3000KP-ACI-4\"-C1F-2092")
("4\"-BAFE614658DD4547E929139B82" "3000KP-ACI-4\"-C1F-2093")
("4\"-2324ECE81C1231481A69174158" "3000KP-ACI-4\"-C1F-2094")
("4\"-00C817BF9EAC414FD33A0898BC" "3000KP-ACI-4\"-C1F-2095")
("4\"-2307CA5F16F1584E3EA9A92C2D" "3000KP-ACI-4\"-C1F-2096")
("3\"-B4BED329F7547C41747BC56068" "3000KP-ACI-3\"-C1F-2097")
("3\"-1D7AA9B246044849A8F92D78E7" "3000KP-ACI-3\"-C1F-2098")
("3\"-26514CC57B494A418148739489" "3000KP-ACI-3\"-C1F-2099")
("3\"-58D3558FD772494B831812DF27" "3000KP-ACI-3\"-C1F-2100")
("3\"-88DAB81932C9FC49D1BA77036E" "3000KP-ACI-3\"-C1F-2101")
("3\"-3C49D987CB3D13425AA825B6E4" "3000KP-ACI-3\"-C1F-2102")
("3\"-1DCB1F725769EE45680A3824AC" "3000KP-ACI-3\"-C1F-2103")
("3\"-932213DBD7FB0142F70A530631" "3000KP-ACI-3\"-C1F-2104")
("3\"-5833EA39D2C2DE4632095B3ABA" "3000KP-ACI-3\"-C1F-2105")
("3\"-EF4AAD1E8C39ED4A46697313C1" "3000KP-ACI-3\"-C1F-2106")
("3\"-623B475A917ECB4E49FAE64DD8" "3000KP-ACI-3\"-C1F-2107")
("3\"-19AED8C44CF3B24B381ACA0A2C" "3000KP-ACI-3\"-C1F-2108")
("3\"-43F6304722DA294C2B1AD622F5" "3000KP-ACI-3\"-C1F-2109")
("3\"-E6C46589D558B9437D3A74D111" "3000KP-ACI-3\"-C1F-2110")
("3\"-2DBD7BA012F7B944EF6B047D2E" "3000KP-ACI-3\"-C1F-2111")
("3\"-A2992B1CD6D2F544B29969E3A6" "3000KP-ACI-3\"-C1F-2112")
("3\"-E64DD8E02E9BBB4C468855ABC9" "3000KP-ACI-3\"-C1F-2113")
("3\"-264E9A19AED8C444CF3A2B3818" "3000KP-ACI-3\"-C1F-2114")
("3\"-427394898B16884B31AA57CEB6" "3000KP-ACI-3\"-C1F-2115")
("3\"-02149D114A923C4E574BCCBD9B" "3000KP-ACI-3\"-C1F-2116")
("3\"-21C31D25FFB7074AE9EAB40ED3" "3000KP-ACI-3\"-C1F-2234")
)) ; Adicione mais pares conforme necessário

    ; Selecionar objetos TEXT, MTEXT e MULTILEADER
    (setq ss (ssget "X" '((0 . "TEXT,MTEXT,MULTILEADER"))))

    ; Verificar se há objetos selecionados
    (if ss
        (progn
            (setq idx 0)
            ; Loop através dos objetos selecionados
            (while (< idx (sslength ss))
                (setq entity (ssname ss idx))
                (if entity
                    (progn
                        (setq obj (vlax-ename->vla-object entity))
                        (cond
                            ; Caso seja um objeto MULTILEADER
                            ((= (vla-get-ObjectName obj) "AcDbMLeader")
                             (setq contentString (vla-get-TextString obj)) ; Obtém o texto do MLeader
                            )
                            ; Caso seja um objeto MTEXT
                            ((= (vla-get-ObjectName obj) "AcDbMText")
                             (setq contentString (vla-get-TextString obj)) ; Obtém o texto do MText
                            )
                            ; Caso seja um objeto TEXT
                            ((= (vla-get-ObjectName obj) "AcDbText")
                             (setq contentString (vla-get-TextString obj)) ; Obtém o texto do Text
                            )
                            ; Outros casos, ignora
                            (T (setq contentString nil))
                        )
                        ; Realizar substituição se o texto foi encontrado
                        (if contentString
                            (progn
                                ; Loop pela lista de substituições
                                (foreach pair substitutions
                                    (setq searchText (car pair))                ; Texto a buscar
                                    (setq replaceText (cadr pair))         ; Texto a substituir
                                    ; Substituir o texto, se encontrado
                                    (if (vl-string-search searchText contentString)
                                        (setq contentString (vl-string-subst replaceText searchText contentString))
                                    )
                                )
                                ; Atualizar o texto no objeto correspondente
                                (cond
                                    ((= (vla-get-ObjectName obj) "AcDbMLeader")
                                     (vla-put-TextString obj contentString)
                                    )
                                    ((= (vla-get-ObjectName obj) "AcDbMText")
                                     (vla-put-TextString obj contentString)
                                    )
                                    ((= (vla-get-ObjectName obj) "AcDbText")
                                     (vla-put-TextString obj contentString)
                                    )
                                )
                            )
                        )
                    )
                )
                (setq idx (1+ idx))
            )
            (princ "\nSubstituições concluídas.")
        )
        (princ "\nNenhum objeto do tipo TEXT, MTEXT ou MULTILEADER encontrado.")
    )
    (princ)
)
(ReplaceTextAndMText)
(c:FINISHHIM)
